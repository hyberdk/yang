submodule Cisco-IOS-XE-eigrp-obsolete {
  belongs-to Cisco-IOS-XE-eigrp {
    prefix ios-eigrp;
  }

  import ietf-inet-types {
    prefix inet;
  }
  import Cisco-IOS-XE-types {
    prefix ios-types;
  }
  import Cisco-IOS-XE-native {
    prefix ios;
  }
  import Cisco-IOS-XE-features {
    prefix ios-features;
  }

  revision 2019-10-01 {
    description
      "Initial revision";
  }

  grouping eigrp-af-topo-redist-grouping {
    container route-map {
      status obsolete;
      description
        "Filter prefixes based on the route-map";
      list rmap-name {
        status obsolete;
        key "rmap-name";
        leaf rmap-name {
          status obsolete;
          description
            "route-map name";
          type string;
        }
      }
    }
    container metric {
      status obsolete;
      description
        "Metric for redistributed routes";
      leaf bandwith {
        status obsolete;
        description
          "Bandwidth metric in Kbits per second";
        type uint32 {
          range "1..4294967295";
        }
      }
      leaf delay {
        status obsolete;
        description
          "EIGRP delay metric, in 10 microsecond units";
        type uint32 {
          range "0..4294967295";
        }
      }
      leaf reliability {
        status obsolete;
        description
          "EIGRP reliability metric where 255 is 100% reliable";
        type uint8 {
          range "0..255";
        }
      }
      leaf Effective {
        status obsolete;
        description
          "EIGRP Effective bandwidth metric (Loading) where 255 is 100% loaded";
        type uint8 {
          range "1..255";
        }
      }
      leaf mtu {
        status obsolete;
        description
          "MTU of the path";
        type uint16 {
          range "1..65535";
        }
      }
    }
  }

  grouping ipv6-router-distribute-list-grouping {
    container distribute-list {
      description
        "Filter networks in routing updates";
      list prefix-list {
        description
          "Filter connections based on an IPv6 prefix-list";
        key "name";
        leaf name {
          type string;
        }
        leaf in {
          description
            "Filter incoming routing updates";
          type empty;
        }
        leaf out {
          description
            "Filter outgoing routing updates";
          type empty;
        }
      }
    }
  }

  grouping ipv6-router-distribute-list-grouping-obsolete {
    container distribute-list {
      status obsolete;
      description
        "Filter networks in routing updates";
      list prefix-list {
        status obsolete;
        description
          "Filter connections based on an IPv6 prefix-list";
        key "name";
        leaf name {
          status obsolete;
          type string;
        }
        leaf in {
          status obsolete;
          description
            "Filter incoming routing updates";
          type empty;
        }
        leaf out {
          status obsolete;
          description
            "Filter outgoing routing updates";
          type empty;
        }
      }
    }
  }

  grouping config-interface-ipv6-eigrp-grouping {
    status obsolete;
    container eigrp {
      status obsolete;
      description
        "Interface command for IPv6 EIGRP. (obsolete, use router-eigrp)";
      leaf as-number {
        status obsolete;
        type uint16;
      }
    }
  }

  grouping eigrp-topology-base-grouping {
    container topology {
      status obsolete;
      description
        "Topology configuration mode";
      container base {
        status obsolete;
        description
          "Base Topology";
        presence "true";
        container distance {
          status obsolete;
          description
            "Define an administrative distance";
          container eigrp {
            status obsolete;
            description
              "EIGRP-IPV6 distance";
            list distance-list {
              status obsolete;
              key "internal-route";
              leaf internal-route {
                status obsolete;
                description
                  "Distance for internal routes";
                type uint8 {
                  range "1..255";
                }
              }
              leaf external-route {
                status obsolete;
                description
                  "Distance for external routes";
                type uint8 {
                  range "1..255";
                }
              }
            }
          }
        }
        container table-map {
          status obsolete;
          description
            "Define Table-Map for setting OMP-TAG into routing table";
          leaf name {
            status obsolete;
            description
              "WORD;;route-map name";
            type string;
          }
          leaf filter {
            status obsolete;
            description
              "Selective route download";
            type empty;
          }
        }
        container distribute-list {
          status obsolete;
          description
            "Filter entries in eigrp updates";
          list prefix-list {
            status obsolete;
            description
              "Filter prefixes in address updates";
            key "prefix-list";
            leaf prefix-list {
              status obsolete;
              description
                "Name of an IP prefix-list";
              type string;
            }
            leaf gateway {
              status obsolete;
              description
                "Filtering incoming address updates based on gateway";
              type empty;
            }
            leaf in {
              status obsolete;
              description
                "Filter incoming service updates";
              type empty;
            }
            leaf out {
              status obsolete;
              description
                "Filter outgoing service updates";
              type empty;
            }
          }
          list route-map {
            status obsolete;
            description
              "Filter prefixes based on the route-map";
            key "name";
            leaf name {
              status obsolete;
              type string;
            }
            leaf in {
              status obsolete;
              description
                "Filter incoming service updates";
              type string;
            }
            leaf out {
              status obsolete;
              description
                "Filter outgoing service updates";
              type string;
            }
          }
        }
        container redistribute {
          status obsolete;
          description
            "Redistribute IPv6 prefixes from another routing protocol";
          container eigrp {
            status obsolete;
            description
              "Enhanced Interior Gateway Routing Protocol (EIGRP)";
            list as-list {
              status obsolete;
              key "autonomous-system";
              leaf autonomous-system {
                status obsolete;
                description
                  "Autonomous system number";
                type uint16 {
                  range "1..65535";
                }
              }
              uses eigrp-af-topo-redist-obsolete-grouping;
            }
          }
          container omp {
            status obsolete;
            if-feature "ios-features:omp";
            description
              "Overlay Management Protocol (OMP)";
            presence "true";
            uses eigrp-af-topo-redist-grouping;
          }
          container nat-route {
            status obsolete;
            if-feature "ios-features:sdwan";
            description
              "NAT Route";
            leaf dia {
              status obsolete;
              description
                "Redistribute NAT Direct Internet Access routes";
              type empty;
            }
            leaf outside {
              status obsolete;
              description
                "Redistribute NAT Outside routes";
              type empty;
            }
            uses eigrp-af-topo-redist-grouping;
          }
          container ospf {
            status obsolete;
            description
              "Open Shortest Path First (OSPFv3)";
            leaf process-id {
              status obsolete;
              description
                "Process ID";
              type uint16 {
                range "1..65535";
              }
            }
            uses eigrp-af-topo-redist-grouping;
          }
          container connected {
            status obsolete;
            description
              "Connected Routes";
            presence "true";
            uses eigrp-af-topo-redist-grouping;
          }
          container static {
            status obsolete;
            description
              "Static Routes";
            presence "true";
            uses eigrp-af-topo-redist-grouping;
          }
          container bgp {
            status obsolete;
            description
              "Border Gateway Protocol (BGP)";
            leaf as-number {
              status obsolete;
              type ios-types:bgp-as-number-type;
            }
            uses eigrp-af-topo-redist-grouping;
          }
        }
        list summary-metric {
          status obsolete;
          description
            "Specify summary to apply metric/filtering";
          key "ipv4-addr-slash-prefix-len";
          leaf ipv4-addr-slash-prefix-len {
            status obsolete;
            description
              "Summary <network>/<length>, e.g., 192.168.0.0/16";
            type inet:ipv4-prefix;
          }
          container metric {
            status obsolete;
            leaf bandwidth-metric {
              status obsolete;
              description
                "Bandwidth metric in Kbits per second";
              type uint32 {
                range "1..4294967295";
              }
            }
            leaf delay-metric {
              status obsolete;
              description
                "delay metric in 10 microsecond units";
              type uint32 {
                range "1..4294967295";
              }
            }
            leaf reliability-metric {
              status obsolete;
              description
                "reliability metric where 255 is 100% reliable";
              type uint8 {
                range "0..255";
              }
            }
            leaf effective-bandwidth-metric {
              status obsolete;
              description
                "Effective bandwidth metric (Loading) where 255 is 100% loaded";
              type uint8 {
                range "0..255";
              }
            }
            leaf mtu {
              status obsolete;
              description
                "MTU of the path";
              type uint16 {
                range "1..65535";
              }
            }
          }
          leaf distance {
            status obsolete;
            description
              "Set administrative distance for summary route";
            type uint8 {
              range "1..255";
            }
          }
        }
      }
    }
  }

  grouping eigrp-address-family-grouping {
    list af-interface {
      status obsolete;
      description
        "Enter Address Family interface configuration";
      key "name";
      leaf name {
        status obsolete;
        type string;
      }
      leaf bandwidth-percent {
        status obsolete;
        description
          "Set percentage of bandwidth percentage limit";
        type uint32 {
          range "1..999999";
        }
      }
      leaf shutdown {
        status obsolete;
        description
          "Shutdown this interface of EIGRP";
        type empty;
      }
      leaf bfd {
        status obsolete;
        description
          "set peer monitoring method to bfd";
        type empty;
      }
      leaf hello-interval {
        status obsolete;
        description
          "Configures hello interval";
        type uint16;
      }
      leaf hold-time {
        status obsolete;
        description
          "Configures hold time";
        type uint16;
      }
      leaf passive-interface {
        status obsolete;
        description
          "Suppress address updates on an interface";
        type boolean;
      }
      leaf split-horizon {
        status obsolete;
        description
          "Perform split horizon";
        type boolean;
      }
      container stub-site {
        status obsolete;
        description
          "Stub-Site";
        leaf wan-interface {
          status obsolete;
          description
            "Wan Interface";
          type empty;
        }
      }
      container authentication {
        status obsolete;
        description
          "authentication subcommands";
        container mode {
          status obsolete;
          description
            "authentication mode";
          leaf md5 {
            status obsolete;
            description
              "Keyed message digest";
            type empty;
          }
          container hmac-sha-256 {
            status obsolete;
            description
              "HMAC-SHA-256 Authentication";
            leaf auth-type {
              status obsolete;
              type uint8;
            }
            leaf auth-key {
              status obsolete;
              type string;
            }
          }
        }
        leaf key-chain {
          status obsolete;
          description
            "key-chain";
          type string;
        }
      }
      list summary-address {
        status obsolete;
        key "prefix";
        leaf prefix {
          status obsolete;
          type union {
            type inet:ipv4-prefix;
            type ios-types:ipv6-prefix;
          }
        }
      }
    }
    container set-as-in-submode {
      status obsolete;
      leaf autonomous-system {
        status obsolete;
        description
          "Specify Address-Family Autonomous System Number?";
        type uint16;
      }
    }
    leaf auto-summary {
      status obsolete;
      description
        "Enable automatic network number summarization";
      type empty;
    }
    container bfd {
      status obsolete;
      description
        "BFD configuration commands";
      leaf all-interfaces {
        status obsolete;
        description
          "Enable BFD on all interfaces";
        type empty;
      }
      container interface {
        status obsolete;
        description
          "Enable BFD on specific interface";
        uses interface-grouping-obsolete {
          status obsolete;
        }
      }
    }
    container default-information {
      status obsolete;
      description
        "Control distribution of default information";
      container in {
        status obsolete;
        description
          "Accept input default routing information";
        presence "true";
        leaf sa-num {
          status obsolete;
          description
            "A standard expanded IP access list number";
          type uint16 {
            range "1300..1999";
          }
        }
        leaf sa-name {
          status obsolete;
          description
            "Standard Access-list name";
          type string;
        }
      }
      container out {
        status obsolete;
        description
          "Accept output default routing information";
        presence "true";
        leaf sa-out-num {
          status obsolete;
          description
            "A standard expanded IP access list number";
          type uint16 {
            range "1300..1999";
          }
        }
        leaf sa-out-name {
          status obsolete;
          description
            "Standard Access-list name";
          type string;
        }
      }
    }
    container default-metric {
      status obsolete;
      description
        "Set metric of redistributed routes";
      list dm-rdr {
        status obsolete;
        key "dm-rdr";
        leaf dm-rdr {
          status obsolete;
          description
            "Bandwidth in Kbits per second";
          type uint32 {
            range "1..4294967295";
          }
        }
        list dm-rdr0 {
          status obsolete;
          key "dm-rdr0";
          leaf dm-rdr0 {
            status obsolete;
            description
              "delay metric in 10 microsecond units";
            type uint32 {
              range "0..4294967295";
            }
          }
          leaf dm-rdr-pct {
            status obsolete;
            description
              "Reliability metric where 255 is 100% reliable";
            type uint8 {
              range "0..255";
            }
          }
        }
      }
    }
    container distance {
      status obsolete;
      description
        "Define an administrative distance";
      list rad-dis {
        status obsolete;
        key "rad-dis";
        leaf rad-dis {
          status obsolete;
          description
            "Set route administrative distance";
          type uint8 {
            range "1..255";
          }
        }
        list ipv4 {
          status obsolete;
          key "ipv4";
          leaf ipv4 {
            status obsolete;
            description
              "IP Source address";
            type inet:ipv4-address;
          }
          leaf ipv40 {
            status obsolete;
            description
              "Wildcard bits";
            type inet:ipv4-address;
          }
        }
      }
      container eigrp {
        status obsolete;
        description
          "Set distance for internal and external routes";
        list di-rt {
          status obsolete;
          key "di-rt";
          leaf di-rt {
            status obsolete;
            description
              "Distance for internal routes";
            type uint8 {
              range "1..255";
            }
          }
          leaf di-rt0 {
            status obsolete;
            description
              "Distance for external routes";
            type uint8 {
              range "1..255";
            }
          }
        }
      }
    }
    container distribute-list {
      status obsolete;
      description
        "Filter entries in eigrp updates";
      list eig-filt {
        status obsolete;
        key "eig-filt";
        leaf eig-filt {
          status obsolete;
          description
            "IP expanded access list number";
          type ios-types:exp-acl-type;
        }
        container in {
          status obsolete;
          description
            "Filter incoming service updates";
          presence "true";
          leaf-list interface_name {
            status obsolete;
            description
              "Interface name";
            type string;
          }
        }
        container out {
          status obsolete;
          description
            "Filter outgoing service updates";
          presence "true";
          leaf-list interface_name {
            status obsolete;
            description
              "Interface name";
            type string;
          }
        }
      }
      container gateway {
        status obsolete;
        description
          "Filtering incoming address updates based on gateway";
        list gw-list {
          status obsolete;
          key "gw-list";
          leaf gw-list {
            status obsolete;
            description
              "Name of an IP prefix-list";
            type string;
          }
          leaf in {
            status obsolete;
            description
              "Filter incoming service updates";
            type empty;
          }
          leaf out {
            status obsolete;
            description
              "Filter outgoing service updates";
            type empty;
          }
        }
      }
      container prefix {
        status obsolete;
        description
          "Filter prefixes in address updates";
        list pl-name {
          status obsolete;
          key "pl-name";
          leaf pl-name {
            status obsolete;
            description
              "Name of an IP prefix-list";
            type string;
          }
          leaf gateway {
            status obsolete;
            description
              "Filtering incoming address updates based on gateway";
            type empty;
          }
          leaf in {
            status obsolete;
            description
              "Filter incoming service updates";
            type empty;
          }
          leaf out {
            status obsolete;
            description
              "Filter outgoing service updates";
            type empty;
          }
        }
      }
      container route-map {
        status obsolete;
        description
          "Filter prefixes based on the route-map";
        list rmap-name {
          status obsolete;
          key "rmap-name";
          leaf rmap-name {
            status obsolete;
            description
              "route-map name";
            type string;
          }
          leaf in {
            status obsolete;
            description
              "Filter incoming service updates";
            type empty;
          }
          leaf out {
            status obsolete;
            description
              "Filter outgoing service updates";
            type empty;
          }
        }
      }
    }
    container eigrp {
      status obsolete;
      description
        "EIGRP Address Family specific commands";
      leaf router-id {
        status obsolete;
        description
          "router id for this EIGRP process";
        type inet:ipv4-address;
      }
      container stub {
        status obsolete;
        description
          "Set address-family in stubbed mode";
        presence "true";
        leaf connected {
          status obsolete;
          description
            "Do advertise connected routes";
          type empty;
        }
        leaf summary {
          status obsolete;
          description
            "Do advertise summary routes";
          type empty;
        }
        leaf redistributed {
          status obsolete;
          description
            "Do advertise redistributed routes";
          type empty;
        }
        leaf leak-map {
          status obsolete;
          description
            "Allow dynamic prefixes based on the leak-map";
          type string;
        }
        leaf receive-only {
          status obsolete;
          description
            "Set receive only neighbor";
          type empty;
        }
        leaf static {
          status obsolete;
          description
            "Do advertise static routes";
          type empty;
        }
      }
      leaf stub-site {
        status obsolete;
        description
          "ASN:nn, Dotted-Decimal:nn or 4BASN:nn  Stub-Site ID in aa:nn format";
        type string;
      }
    }
    leaf maximum-paths {
      status obsolete;
      description
        "Number of paths";
      type uint8 {
        range "1..32";
      }
    }
    container metric {
      status obsolete;
      description
        "Modify metrics and parameters for advertisement";
      leaf maximum-hops {
        status obsolete;
        description
          "Hop count";
        type uint8 {
          range "1..255";
        }
      }
      leaf weights {
        status obsolete;
        description
          "Type (Only TOS 0 supported)";
        type uint8 {
          range "0..8";
        }
      }
    }
    container neighbor {
      status obsolete;
      description
        "Specify a neighbor router";
      list ipv4 {
        status obsolete;
        key "ipv4";
        leaf ipv4 {
          status obsolete;
          description
            "Neighbor address";
          type inet:ipv4-address;
        }
        container interface {
          status obsolete;
          description
            "Specify interface for global address";
          uses interface-grouping-obsolete {
            status obsolete;
          }
        }
      }
    }
    list network {
      status obsolete;
      description
        "Enable routing on an IP network";
      key "number";
      leaf number {
        status obsolete;
        description
          "Network number";
        type inet:ipv4-address;
      }
      leaf wild-card {
        status obsolete;
        description
          "EIGRP wild card bits";
        type inet:ipv4-address;
      }
    }
    leaf nsf {
      status obsolete;
      description
        "Non-stop forwarding";
      type empty;
    }
    container offset-list {
      status obsolete;
      description
        "Add or subtract offset from EIGRP metrics";
      list nsr-list {
        status obsolete;
        key "nsr-list";
        leaf nsr-list {
          status obsolete;
          description
            "Access list of networks to apply offset (extended range)";
          type uint16 {
            range "1300..1999";
          }
        }
        leaf in {
          status obsolete;
          description
            "Perform offset on incoming updates";
          type empty;
        }
        leaf out {
          status obsolete;
          description
            "Perform offset on outgoing updates";
          type empty;
        }
      }
      list ol-acl {
        status obsolete;
        key "ol-acl";
        leaf ol-acl {
          status obsolete;
          description
            "Access-list name";
          type string;
        }
        leaf in {
          status obsolete;
          description
            "Perform offset on incoming updates";
          type empty;
        }
        leaf out {
          status obsolete;
          description
            "Perform offset on outgoing updates";
          type empty;
        }
      }
    }
    container redistribute {
      status obsolete;
      description
        "Redistribute IPv4 routes from another routing protocol";
      list bgp {
        status obsolete;
        description
          "Border Gateway Protocol (BGP)";
        key "rdr-as";
        leaf rdr-as {
          status obsolete;
          description
            "Autonomous system number";
          type ios-types:bgp-as-number-type;
        }
        container metric {
          status obsolete;
          description
            "Metric for redistributed routes";
          leaf bandwith {
            status obsolete;
            description
              "Bandwidth metric in Kbits per second";
            type uint32 {
              range "1..4294967295";
            }
          }
          leaf delay {
            status obsolete;
            description
              "EIGRP delay metric, in 10 microsecond units";
            type uint32 {
              range "0..4294967295";
            }
          }
          leaf reliability {
            status obsolete;
            description
              "EIGRP reliability metric where 255 is 100% reliable";
            type uint8 {
              range "0..255";
            }
          }
          leaf Effective {
            status obsolete;
            description
              "EIGRP Effective bandwidth metric (Loading) where 255 is 100% loaded";
            type uint8 {
              range "1..255";
            }
          }
          leaf mtu {
            status obsolete;
            description
              "EIGRP MTU of the path";
            type uint16 {
              range "1..65535";
            }
          }
        }
        leaf route-map {
          status obsolete;
          description
            "Route map reference";
          type string;
        }
        leaf rd-LESSER_1_PERIOD_0-XX_PERIOD_YY_GREATER_ {
          status obsolete;
          description
            "Autonomous system number";
          type empty;
        }
      }
      container connected {
        status obsolete;
        description
          "Connected";
        presence "true";
        leaf metric {
          status obsolete;
          description
            "Metric for redistributed routes";
          type empty;
        }
        leaf route-map {
          status obsolete;
          description
            "Route map reference";
          type empty;
        }
      }
      leaf eigrp {
        status obsolete;
        description
          "Autonomous system number";
        type uint16 {
          range "1..65535";
        }
      }
      container isis {
        status obsolete;
        description
          "ISO IS-IS";
        presence "true";
        leaf is-tag {
          status obsolete;
          description
            "ISO routing area tag";
          type string;
        }
        leaf level-1 {
          status obsolete;
          description
            "IS-IS level-1 routes only";
          type empty;
        }
        leaf level-1-2 {
          status obsolete;
          description
            "IS-IS level-1 and level-2 routes";
          type empty;
        }
        leaf level-2 {
          status obsolete;
          description
            "IS-IS level-2 routes only";
          type empty;
        }
        leaf metric {
          status obsolete;
          description
            "Metric for redistributed routes";
          type empty;
        }
        leaf route-map {
          status obsolete;
          description
            "Route map reference";
          type empty;
        }
      }
      container lisp {
        status obsolete;
        description
          "Locator ID Separation Protocol (LISP)";
        presence "true";
        leaf metric {
          status obsolete;
          description
            "Metric for redistributed routes";
          type empty;
        }
        leaf route-map {
          status obsolete;
          description
            "Route map reference";
          type empty;
        }
      }
      container mobile {
        status obsolete;
        description
          "Mobile routes";
        presence "true";
        leaf metric {
          status obsolete;
          description
            "Metric for redistributed routes";
          type empty;
        }
        leaf route-map {
          status obsolete;
          description
            "Route map reference";
          type empty;
        }
      }
      container odr {
        status obsolete;
        description
          "On Demand stub Routes";
        presence "true";
        leaf metric {
          status obsolete;
          description
            "Metric for redistributed routes";
          type empty;
        }
        leaf route-map {
          status obsolete;
          description
            "Route map reference";
          type empty;
        }
      }
      leaf ospf {
        status obsolete;
        description
          "Process ID";
        type uint16 {
          range "1..65535";
        }
      }
      container rip {
        status obsolete;
        description
          "Routing Information Protocol (RIP)";
        presence "true";
        leaf metric {
          status obsolete;
          description
            "Metric for redistributed routes";
          type empty;
        }
        leaf route-map {
          status obsolete;
          description
            "Route map reference";
          type empty;
        }
      }
      container static {
        status obsolete;
        description
          "Static routes";
        presence "true";
        leaf metric {
          status obsolete;
          description
            "Metric for redistributed routes";
          type empty;
        }
        leaf route-map {
          status obsolete;
          description
            "Route map reference";
          type empty;
        }
      }
      container vrf {
        status obsolete;
        description
          "Specify a source virtual routing/forwarding instance";
        leaf name {
          status obsolete;
          description
            "Virtual Routing/Forwarding instance name";
          type string;
        }
        leaf global {
          status obsolete;
          description
            "global VRF";
          type empty;
        }
      }
    }
    leaf shutdown {
      status obsolete;
      description
        "Shutdown this instance of EIGRP";
      type empty;
    }
    container summary-metric {
      status obsolete;
      description
        "Specify summary to apply metric/filtering";
      list ipv4 {
        status obsolete;
        key "ipv4";
        leaf ipv4 {
          status obsolete;
          description
            "Summary to configure static metric";
          type inet:ipv4-address;
        }
        leaf mask {
          status obsolete;
          description
            "Network mask";
          type inet:ipv4-address;
        }
      }
      leaf A_PERIOD_B_PERIOD_C_PERIOD_D_SLASH_nn {
        status obsolete;
        description
          "Summary <network>/<length>, e.g., 192.168.0.0/16";
        type empty;
      }
    }
    container timers {
      status obsolete;
      description
        "Adjust routing timers";
      container active-time {
        status obsolete;
        description
          "time limit for active state";
        leaf atimer {
          status obsolete;
          description
            "active state time limit in minutes";
          type uint16 {
            range "1..65535";
          }
        }
        leaf disabled {
          status obsolete;
          description
            "disable time limit for active state";
          type empty;
        }
      }
      container graceful-restart {
        status obsolete;
        description
          "EIGRP Graceful Restart timer";
        leaf purge-time {
          status obsolete;
          description
            "EIGRP stale route purge time";
          type empty;
        }
      }
      container nsf {
        status obsolete;
        description
          "EIGRP NSF timer";
        leaf converge {
          status obsolete;
          description
            "EIGRP time limit for convergence after switchover";
          type empty;
        }
        leaf signal {
          status obsolete;
          description
            "EIGRP time limit for signaling NSF restart";
          type empty;
        }
      }
    }
    container traffic-share {
      status obsolete;
      description
        "How to compute traffic share over alternate paths";
      leaf balanced {
        status obsolete;
        description
          "Share inversely proportional to metric";
        type empty;
      }
      container min {
        status obsolete;
        description
          "All traffic shared among min metric paths";
        leaf across-interfaces {
          status obsolete;
          description
            "Use different interfaces for equal-cost paths";
          type empty;
        }
      }
    }
    leaf variance {
      status obsolete;
      description
        "Metric variance multiplier";
      type uint8 {
        range "1..128";
      }
    }
  }

  grouping config-router-eigrp-grouping {
    status obsolete;
    list eigrp {
      status obsolete;
      description
        "Enhanced Interior Gateway Routing Protocol (EIGRP) (obsolete, use router-eigrp)";
      key "id";
      leaf id {
        status obsolete;
        description
          "Autonomous System ID";
        type union {
          type uint16 {
            range "1..65535";
          }
          type string;
        }
      }
      container passive-interface {
        status obsolete;
        description
          "Suppress routing updates on an interface";
        leaf interface {
          status obsolete;
          description
            "interface name";
          type string;
        }
        leaf Tunnel {
          status obsolete;
          description
            "Tunnel interface number";
          type uint32 {
            range "0..2147483647";
          }
        }
        leaf Vlan {
          status obsolete;
          description
            "Vlan interface number";
          type uint16 {
            range "1..4094";
          }
        }
        leaf default {
          status obsolete;
          description
            "Suppress routing updates on all interfaces";
          type empty;
        }
      }
      list address-family {
        status obsolete;
        description
          "Enter Address Family command mode";
        key "type";
        leaf type {
          status obsolete;
          type enumeration {
            enum "ipv4";
            enum "ipv6";
          }
        }
        list af-ip-list {
          status obsolete;
          description
            "Address family IPv4/IPv6";
          key "unicast-multicast";
          leaf unicast-multicast {
            status obsolete;
            type enumeration {
              enum "unicast";
              enum "multicast";
            }
          }
          leaf autonomous-system {
            status obsolete;
            description
              "Specify Address-Family Autonomous System Number";
            type uint16 {
              range "1..65535";
            }
          }
          uses eigrp-address-family-obsolete-grouping;
          uses eigrp-topology-base-grouping;
        }
        list af-ip-vrf-list {
          status obsolete;
          description
            "Address family IPv4/IPv6 VRF";
          key "vrf";
          leaf vrf {
            status obsolete;
            must "/ios:native/ios:vrf/ios:definition[ios:name=current()] or /ios:native/ios:ip/ios:vrf[ios:name=current()]" {
              error-message "VRF must be created 1st, deleted last";
            }
            type string;
          }
          leaf unicast-multicast {
            status obsolete;
            type enumeration {
              enum "unicast";
              enum "multicast";
            }
          }
          leaf autonomous-system {
            status obsolete;
            description
              "Specify Address-Family Autonomous System Number?";
            type uint16;
          }
          uses eigrp-address-family-grouping;
          uses eigrp-topology-base-grouping;
        }
      }
      uses eigrp-address-family-grouping;
    }
  }

  grouping config-router-ipv6-eigrp-grouping {
    status obsolete;
    container default-metric {
      status obsolete;
      description
        "Set metric of redistributed routes";
      leaf dm-rdr {
        status obsolete;
        description
          "Bandwidth in Kbits per second";
        type uint32 {
          range "1..4294967295";
        }
      }
      leaf dm-rdr0 {
        status obsolete;
        description
          "delay metric in 10 microsecond units";
        type uint32 {
          range "0..4294967295";
        }
      }
      leaf dm-rdr-pct {
        status obsolete;
        description
          "Reliability metric where 255 is 100% reliable";
        type uint8 {
          range "0..255";
        }
      }
      leaf effective-bandwith-metric {
        status obsolete;
        description
          "Effective bandwidth metric (Loading) where 255 is 100% loaded";
        type uint8;
      }
      leaf mtu {
        status obsolete;
        description
          "Maximum Transmission Unit metric of the path ";
        type uint16;
      }
    }
    container distance {
      status obsolete;
      description
        "Define an administrative distance";
      container eigrp {
        status obsolete;
        description
          "EIGRP-IPV6 distance";
        leaf internal-route {
          status obsolete;
          description
            "Distance for internal routes";
          type uint8;
        }
        leaf external-route {
          status obsolete;
          description
            "Distance for external routes";
          type uint8;
        }
      }
    }
    uses ipv6-router-distribute-list-grouping-obsolete {
      status obsolete;
    }
    container eigrp {
      status obsolete;
      description
        "EIGRP specific commands";
      leaf router-id {
        status obsolete;
        description
          "router id for this EIGRP process";
        type inet:ipv4-address;
      }
    }
    list passive-interface {
      status obsolete;
      description
        "Suppress routing updates on an interface";
      key "name";
      leaf name {
        status obsolete;
        type union {
          type string;
          type enumeration {
            enum "default";
          }
        }
      }
    }
  }

  grouping config-route-tag-grouping {
    container list {
      list rt-name {
        key "rt-name";
        leaf rt-name {
          type string;
        }
        container deny {
          list ipv4 {
            key "ipv4";
            leaf ipv4 {
              type inet:ipv4-address;
            }
            leaf mask {
              type inet:ipv4-address;
            }
          }
        }
        container permit {
          list ipv4 {
            key "ipv4";
            leaf ipv4 {
              type inet:ipv4-address;
            }
            leaf mask {
              type inet:ipv4-address;
            }
          }
        }
        container seq {
          list seq-num {
            key "seq-num";
            leaf seq-num {
              type uint32 {
                range "1..4294967294";
              }
            }
            container deny {
              leaf ipv4 {
                type inet:ipv4-address;
              }
              leaf mask {
                type inet:ipv4-address;
              }
            }
            container permit {
              leaf ipv4 {
                type inet:ipv4-address;
              }
              leaf mask {
                type inet:ipv4-address;
              }
            }
          }
        }
      }
    }
    container notation {
      leaf dotted-decimal {
        type empty;
      }
    }
  }

  grouping interface-grouping-obsolete {
    status obsolete;
    choice interface-choice {
      status obsolete;
      leaf AppNav-Compress {
        status obsolete;
        description
          "Service-Context Virtual Interface Compress";
        type uint16;
      }
      leaf AppNav-UnCompress {
        status obsolete;
        description
          "Service-Context Virtual Interface UnCompress";
        type uint16;
      }
      leaf ATM {
        status obsolete;
        description
          "ATM interface";
        type string;
      }
      container ATM-subinterface {
        status obsolete;
        leaf ATM {
          status obsolete;
          type string;
        }
      }
      leaf ATM-ACR {
        status obsolete;
        description
          "ATM-ACR interface";
        type string {
          pattern "[0-9]";
        }
      }
      container ATM-ACRsubinterface {
        status obsolete;
        leaf ATM-ACR {
          status obsolete;
          type string {
            pattern "[0-9]\\.([0-9]/){3}[0-9]";
          }
        }
      }
      leaf BDI {
        status obsolete;
        description
          "Bridge-Domain interface";
        type string;
      }
      leaf CEM {
        status obsolete;
        description
          "CEM interface";
        type string {
          pattern "([0-9]/){2}[0-9]";
        }
      }
      leaf CEM-ACR {
        status obsolete;
        description
          "CEM-ACR interface";
        type uint8 {
          range "0..255";
        }
      }
      leaf Embedded-Service-Engine {
        status obsolete;
        description
          "cisco embedded service engine module";
        type string;
      }
      leaf Ethernet {
        status obsolete;
        description
          "IEEE 802.3";
        type string;
      }
      leaf FastEthernet {
        status obsolete;
        description
          "FastEthernet IEEE 802.3";
        type string;
      }
      leaf GigabitEthernet {
        status obsolete;
        description
          "GigabitEthernet IEEE 802.3z";
        type string;
      }
      leaf FiveGigabitEthernet {
        status obsolete;
        description
          "Five GigabitEthernet ";
        type string;
      }
      leaf AppGigabitEthernet {
        status obsolete;
        description
          "App-hosting Gigabit Ethernet IEEE 802.3z";
        type string;
      }
      leaf TwentyFiveGigabitEthernet {
        status obsolete;
        description
          "Twenty Five GigabitEthernet ";
        type string;
      }
      leaf TwentyFiveGigE {
        status obsolete;
        description
          "Twenty Five GigabitEthernet ";
        type string;
      }
      leaf TwoGigabitEthernet {
        status obsolete;
        description
          "Two GigabitEthernet ";
        type string;
      }
      leaf FortyGigabitEthernet {
        status obsolete;
        description
          "Forty GigabitEthernet ";
        type string;
      }
      leaf HundredGigE {
        status obsolete;
        description
          "Hundred GigabitEthernet";
        type string;
      }
      leaf LISP {
        status obsolete;
        description
          "Locator/ID Separation Protocol Virtual Interface";
        type string;
      }
      container LISP-subinterface {
        status obsolete;
        description
          "Locator/ID Separation Protocol Virtual Interface";
        leaf LISP {
          status obsolete;
          type string {
            pattern "[0-9]*(. ?[1-9][0-9]*)*";
          }
        }
      }
      leaf Loopback {
        status obsolete;
        description
          "Loopback interface";
        type uint32;
      }
      leaf Multilink {
        status obsolete;
        description
          "Multilink-group interface";
        type uint16;
      }
      leaf nve {
        status obsolete;
        description
          "Network virtualization endpoint interface";
        type uint16;
      }
      leaf overlay {
        status obsolete;
        description
          "Overlay interface";
        type uint16;
      }
      leaf Port-channel {
        status obsolete;
        description
          "Ethernet Channel of interfaces";
        type uint32;
      }
      container Port-channel-subinterface {
        status obsolete;
        leaf Port-channel {
          status obsolete;
          type string;
        }
      }
      leaf pseudowire {
        status obsolete;
        description
          "Pseudowire Interface";
        type uint32;
      }
      leaf SM {
        status obsolete;
        description
          "SM Interface";
        type string;
      }
      leaf Cellular {
        status obsolete;
        description
          "Cellular Interface";
        type string;
      }
      leaf Dialer {
        status obsolete;
        description
          "Dialer Interface";
        type string;
      }
      leaf Serial {
        status obsolete;
        description
          "Serial interface";
        type string;
      }
      leaf TenGigabitEthernet {
        status obsolete;
        description
          "Ten Gigabit Ethernet";
        type string;
      }
      leaf Tunnel {
        status obsolete;
        description
          "Tunnel interface";
        type uint32;
      }
      leaf Virtual-Template {
        status obsolete;
        description
          "Virtual Template interface";
        type uint16;
      }
      leaf Vlan {
        status obsolete;
        description
          "Iosxr Vlans";
        type uint16;
      }
      leaf VirtualPortGroup {
        status obsolete;
        description
          "Virtual Port Group";
        type uint16;
      }
      leaf vasileft {
        status obsolete;
        description
          "vasileft";
        type uint16;
      }
      leaf vasiright {
        status obsolete;
        description
          "vasiright";
        type uint16;
      }
      leaf BD-VIF {
        status obsolete;
        description
          "Bridge-Domain Virtual IP interface";
        type string;
      }
    }
  }

  grouping eigrp-af-topo-redist-obsolete-grouping {
    container route-map {
      status obsolete;
      description
        "Filter prefixes based on the route-map";
      list rmap-name {
        status obsolete;
        key "rmap-name";
        leaf rmap-name {
          status obsolete;
          description
            "route-map name";
          type string;
        }
      }
    }
    container metric {
      status obsolete;
      description
        "Metric for redistributed routes";
      leaf bandwith {
        status obsolete;
        description
          "Bandwidth metric in Kbits per second";
        type uint32 {
          range "1..4294967295";
        }
      }
      leaf delay {
        status obsolete;
        description
          "EIGRP delay metric, in 10 microsecond units";
        type uint32 {
          range "0..4294967295";
        }
      }
      leaf reliability {
        status obsolete;
        description
          "EIGRP reliability metric where 255 is 100% reliable";
        type uint8 {
          range "0..255";
        }
      }
      leaf Effective {
        status obsolete;
        description
          "EIGRP Effective bandwidth metric (Loading) where 255 is 100% loaded";
        type uint8 {
          range "1..255";
        }
      }
      leaf mtu {
        status obsolete;
        description
          "MTU of the path";
        type uint16 {
          range "1..65535";
        }
      }
    }
  }

  grouping eigrp-address-family-obsolete-grouping {
    list af-interface {
      status obsolete;
      description
        "Enter Address Family interface configuration";
      key "name";
      leaf name {
        status obsolete;
        type string;
      }
      leaf bandwidth-percent {
        status obsolete;
        description
          "Set percentage of bandwidth percentage limit";
        type uint32 {
          range "1..999999";
        }
      }
      leaf shutdown {
        status obsolete;
        description
          "Shutdown this interface of EIGRP";
        type empty;
      }
      leaf bfd {
        status obsolete;
        description
          "set peer monitoring method to bfd";
        type empty;
      }
      leaf hello-interval {
        status obsolete;
        description
          "Configures hello interval";
        type uint16;
      }
      leaf hold-time {
        status obsolete;
        description
          "Configures hold time";
        type uint16;
      }
      leaf passive-interface {
        status obsolete;
        description
          "Suppress address updates on an interface";
        type boolean;
      }
      leaf split-horizon {
        status obsolete;
        description
          "Perform split horizon";
        type boolean;
      }
      container stub-site {
        status obsolete;
        description
          "Stub-Site";
        leaf wan-interface {
          status obsolete;
          description
            "Wan Interface";
          type empty;
        }
      }
      container authentication {
        status obsolete;
        description
          "authentication subcommands";
        container mode {
          status obsolete;
          description
            "authentication mode";
          leaf md5 {
            status obsolete;
            description
              "Keyed message digest";
            type empty;
          }
          container hmac-sha-256 {
            status obsolete;
            description
              "HMAC-SHA-256 Authentication";
            leaf auth-type {
              status obsolete;
              type uint8;
            }
            leaf auth-key {
              status obsolete;
              type string;
            }
          }
        }
        leaf key-chain {
          status obsolete;
          description
            "key-chain";
          type string;
        }
      }
      list summary-address {
        status obsolete;
        key "prefix";
        leaf prefix {
          status obsolete;
          type union {
            type inet:ipv4-prefix;
            type ios-types:ipv6-prefix;
          }
        }
      }
    }
    container set-as-in-submode {
      status obsolete;
      leaf autonomous-system {
        status obsolete;
        description
          "Specify Address-Family Autonomous System Number?";
        type uint16;
      }
    }
    leaf auto-summary {
      status obsolete;
      description
        "Enable automatic network number summarization";
      type empty;
    }
    container bfd {
      status obsolete;
      description
        "BFD configuration commands";
      leaf all-interfaces {
        status obsolete;
        description
          "Enable BFD on all interfaces";
        type empty;
      }
      container interface {
        status obsolete;
        description
          "Enable BFD on specific interface";
        uses interface-grouping-obsolete {
          status obsolete;
        }
      }
    }
    container default-information {
      status obsolete;
      description
        "Control distribution of default information";
      container in {
        status obsolete;
        description
          "Accept input default routing information";
        presence "true";
        leaf sa-num {
          status obsolete;
          description
            "A standard expanded IP access list number";
          type uint16 {
            range "1300..1999";
          }
        }
        leaf sa-name {
          status obsolete;
          description
            "Standard Access-list name";
          type string;
        }
      }
      container out {
        status obsolete;
        description
          "Accept output default routing information";
        presence "true";
        leaf sa-out-num {
          status obsolete;
          description
            "A standard expanded IP access list number";
          type uint16 {
            range "1300..1999";
          }
        }
        leaf sa-out-name {
          status obsolete;
          description
            "Standard Access-list name";
          type string;
        }
      }
    }
    container default-metric {
      status obsolete;
      description
        "Set metric of redistributed routes";
      list dm-rdr {
        status obsolete;
        key "dm-rdr";
        leaf dm-rdr {
          status obsolete;
          description
            "Bandwidth in Kbits per second";
          type uint32 {
            range "1..4294967295";
          }
        }
        list dm-rdr0 {
          status obsolete;
          key "dm-rdr0";
          leaf dm-rdr0 {
            status obsolete;
            description
              "delay metric in 10 microsecond units";
            type uint32 {
              range "0..4294967295";
            }
          }
          leaf dm-rdr-pct {
            status obsolete;
            description
              "Reliability metric where 255 is 100% reliable";
            type uint8 {
              range "0..255";
            }
          }
        }
      }
    }
    container distance {
      status obsolete;
      description
        "Define an administrative distance";
      list rad-dis {
        status obsolete;
        key "rad-dis";
        leaf rad-dis {
          status obsolete;
          description
            "Set route administrative distance";
          type uint8 {
            range "1..255";
          }
        }
        list ipv4 {
          status obsolete;
          key "ipv4";
          leaf ipv4 {
            status obsolete;
            description
              "IP Source address";
            type inet:ipv4-address;
          }
          leaf ipv40 {
            status obsolete;
            description
              "Wildcard bits";
            type inet:ipv4-address;
          }
        }
      }
      container eigrp {
        status obsolete;
        description
          "Set distance for internal and external routes";
        list di-rt {
          status obsolete;
          key "di-rt";
          leaf di-rt {
            status obsolete;
            description
              "Distance for internal routes";
            type uint8 {
              range "1..255";
            }
          }
          leaf di-rt0 {
            status obsolete;
            description
              "Distance for external routes";
            type uint8 {
              range "1..255";
            }
          }
        }
      }
    }
    container distribute-list {
      status obsolete;
      description
        "Filter entries in eigrp updates";
      list eig-filt {
        status obsolete;
        key "eig-filt";
        leaf eig-filt {
          status obsolete;
          description
            "IP expanded access list number";
          type ios-types:exp-acl-type;
        }
        container in {
          status obsolete;
          description
            "Filter incoming service updates";
          presence "true";
          leaf-list interface_name {
            status obsolete;
            description
              "Interface name";
            type string;
          }
        }
        container out {
          status obsolete;
          description
            "Filter outgoing service updates";
          presence "true";
          leaf-list interface_name {
            status obsolete;
            description
              "Interface name";
            type string;
          }
        }
      }
      container gateway {
        status obsolete;
        description
          "Filtering incoming address updates based on gateway";
        list gw-list {
          status obsolete;
          key "gw-list";
          leaf gw-list {
            status obsolete;
            description
              "Name of an IP prefix-list";
            type string;
          }
          leaf in {
            status obsolete;
            description
              "Filter incoming service updates";
            type empty;
          }
          leaf out {
            status obsolete;
            description
              "Filter outgoing service updates";
            type empty;
          }
        }
      }
      container prefix {
        status obsolete;
        description
          "Filter prefixes in address updates";
        list pl-name {
          status obsolete;
          key "pl-name";
          leaf pl-name {
            status obsolete;
            description
              "Name of an IP prefix-list";
            type string;
          }
          leaf gateway {
            status obsolete;
            description
              "Filtering incoming address updates based on gateway";
            type empty;
          }
          leaf in {
            status obsolete;
            description
              "Filter incoming service updates";
            type empty;
          }
          leaf out {
            status obsolete;
            description
              "Filter outgoing service updates";
            type empty;
          }
        }
      }
      container route-map {
        status obsolete;
        description
          "Filter prefixes based on the route-map";
        list rmap-name {
          status obsolete;
          key "rmap-name";
          leaf rmap-name {
            status obsolete;
            description
              "route-map name";
            type string;
          }
          leaf in {
            status obsolete;
            description
              "Filter incoming service updates";
            type empty;
          }
          leaf out {
            status obsolete;
            description
              "Filter outgoing service updates";
            type empty;
          }
        }
      }
    }
    container eigrp {
      status obsolete;
      description
        "EIGRP Address Family specific commands";
      leaf router-id {
        status obsolete;
        description
          "router id for this EIGRP process";
        type inet:ipv4-address;
      }
      container stub {
        status obsolete;
        description
          "Set address-family in stubbed mode";
        presence "true";
        leaf connected {
          status obsolete;
          description
            "Do advertise connected routes";
          type empty;
        }
        leaf summary {
          status obsolete;
          description
            "Do advertise summary routes";
          type empty;
        }
        leaf redistributed {
          status obsolete;
          description
            "Do advertise redistributed routes";
          type empty;
        }
        leaf leak-map {
          status obsolete;
          description
            "Allow dynamic prefixes based on the leak-map";
          type string;
        }
        leaf receive-only {
          status obsolete;
          description
            "Set receive only neighbor";
          type empty;
        }
        leaf static {
          status obsolete;
          description
            "Do advertise static routes";
          type empty;
        }
      }
      leaf stub-site {
        status obsolete;
        description
          "ASN:nn, Dotted-Decimal:nn or 4BASN:nn  Stub-Site ID in aa:nn format";
        type string;
      }
    }
    leaf maximum-paths {
      status obsolete;
      description
        "Number of paths";
      type uint8 {
        range "1..32";
      }
    }
    container metric {
      status obsolete;
      description
        "Modify metrics and parameters for advertisement";
      leaf maximum-hops {
        status obsolete;
        description
          "Hop count";
        type uint8 {
          range "1..255";
        }
      }
      leaf weights {
        status obsolete;
        description
          "Type (Only TOS 0 supported)";
        type uint8 {
          range "0..8";
        }
      }
    }
    container neighbor {
      status obsolete;
      description
        "Specify a neighbor router";
      list ipv4 {
        status obsolete;
        key "ipv4";
        leaf ipv4 {
          status obsolete;
          description
            "Neighbor address";
          type inet:ipv4-address;
        }
        container interface {
          status obsolete;
          description
            "Specify interface for global address";
          uses interface-grouping-obsolete {
            status obsolete;
          }
        }
      }
    }
    list network {
      status obsolete;
      description
        "Enable routing on an IP network";
      key "number";
      leaf number {
        status obsolete;
        description
          "Network number";
        type inet:ipv4-address;
      }
      leaf wild-card {
        status obsolete;
        description
          "EIGRP wild card bits";
        type inet:ipv4-address;
      }
    }
    leaf nsf {
      status obsolete;
      description
        "Non-stop forwarding";
      type empty;
    }
    container offset-list {
      status obsolete;
      description
        "Add or subtract offset from EIGRP metrics";
      list nsr-list {
        status obsolete;
        key "nsr-list";
        leaf nsr-list {
          status obsolete;
          description
            "Access list of networks to apply offset (extended range)";
          type uint16 {
            range "1300..1999";
          }
        }
        leaf in {
          status obsolete;
          description
            "Perform offset on incoming updates";
          type empty;
        }
        leaf out {
          status obsolete;
          description
            "Perform offset on outgoing updates";
          type empty;
        }
      }
      list ol-acl {
        status obsolete;
        key "ol-acl";
        leaf ol-acl {
          status obsolete;
          description
            "Access-list name";
          type string;
        }
        leaf in {
          status obsolete;
          description
            "Perform offset on incoming updates";
          type empty;
        }
        leaf out {
          status obsolete;
          description
            "Perform offset on outgoing updates";
          type empty;
        }
      }
    }
    container redistribute {
      status obsolete;
      description
        "Redistribute IPv4 routes from another routing protocol";
      list bgp {
        status obsolete;
        description
          "Border Gateway Protocol (BGP)";
        key "rdr-as";
        leaf rdr-as {
          status obsolete;
          description
            "Autonomous system number";
          type ios-types:bgp-as-number-type;
        }
        container metric {
          status obsolete;
          description
            "Metric for redistributed routes";
          leaf bandwith {
            status obsolete;
            description
              "Bandwidth metric in Kbits per second";
            type uint32 {
              range "1..4294967295";
            }
          }
          leaf delay {
            status obsolete;
            description
              "EIGRP delay metric, in 10 microsecond units";
            type uint32 {
              range "0..4294967295";
            }
          }
          leaf reliability {
            status obsolete;
            description
              "EIGRP reliability metric where 255 is 100% reliable";
            type uint8 {
              range "0..255";
            }
          }
          leaf Effective {
            status obsolete;
            description
              "EIGRP Effective bandwidth metric (Loading) where 255 is 100% loaded";
            type uint8 {
              range "1..255";
            }
          }
          leaf mtu {
            status obsolete;
            description
              "EIGRP MTU of the path";
            type uint16 {
              range "1..65535";
            }
          }
        }
        leaf route-map {
          status obsolete;
          description
            "Route map reference";
          type string;
        }
        leaf rd-LESSER_1_PERIOD_0-XX_PERIOD_YY_GREATER_ {
          status obsolete;
          description
            "Autonomous system number";
          type empty;
        }
      }
      container connected {
        status obsolete;
        description
          "Connected";
        presence "true";
        leaf metric {
          status obsolete;
          description
            "Metric for redistributed routes";
          type empty;
        }
        leaf route-map {
          status obsolete;
          description
            "Route map reference";
          type empty;
        }
      }
      leaf eigrp {
        status obsolete;
        description
          "Autonomous system number";
        type uint16 {
          range "1..65535";
        }
      }
      container isis {
        status obsolete;
        description
          "ISO IS-IS";
        presence "true";
        leaf is-tag {
          status obsolete;
          description
            "ISO routing area tag";
          type string;
        }
        leaf level-1 {
          status obsolete;
          description
            "IS-IS level-1 routes only";
          type empty;
        }
        leaf level-1-2 {
          status obsolete;
          description
            "IS-IS level-1 and level-2 routes";
          type empty;
        }
        leaf level-2 {
          status obsolete;
          description
            "IS-IS level-2 routes only";
          type empty;
        }
        leaf metric {
          status obsolete;
          description
            "Metric for redistributed routes";
          type empty;
        }
        leaf route-map {
          status obsolete;
          description
            "Route map reference";
          type empty;
        }
      }
      container lisp {
        status obsolete;
        description
          "Locator ID Separation Protocol (LISP)";
        presence "true";
        leaf metric {
          status obsolete;
          description
            "Metric for redistributed routes";
          type empty;
        }
        leaf route-map {
          status obsolete;
          description
            "Route map reference";
          type empty;
        }
      }
      container mobile {
        status obsolete;
        description
          "Mobile routes";
        presence "true";
        leaf metric {
          status obsolete;
          description
            "Metric for redistributed routes";
          type empty;
        }
        leaf route-map {
          status obsolete;
          description
            "Route map reference";
          type empty;
        }
      }
      container odr {
        status obsolete;
        description
          "On Demand stub Routes";
        presence "true";
        leaf metric {
          status obsolete;
          description
            "Metric for redistributed routes";
          type empty;
        }
        leaf route-map {
          status obsolete;
          description
            "Route map reference";
          type empty;
        }
      }
      leaf ospf {
        status obsolete;
        description
          "Process ID";
        type uint16 {
          range "1..65535";
        }
      }
      container rip {
        status obsolete;
        description
          "Routing Information Protocol (RIP)";
        presence "true";
        leaf metric {
          status obsolete;
          description
            "Metric for redistributed routes";
          type empty;
        }
        leaf route-map {
          status obsolete;
          description
            "Route map reference";
          type empty;
        }
      }
      container static {
        status obsolete;
        description
          "Static routes";
        presence "true";
        leaf metric {
          status obsolete;
          description
            "Metric for redistributed routes";
          type empty;
        }
        leaf route-map {
          status obsolete;
          description
            "Route map reference";
          type empty;
        }
      }
      container vrf {
        status obsolete;
        description
          "Specify a source virtual routing/forwarding instance";
        leaf name {
          status obsolete;
          description
            "Virtual Routing/Forwarding instance name";
          type string;
        }
        leaf global {
          status obsolete;
          description
            "global VRF";
          type empty;
        }
      }
    }
    leaf shutdown {
      status obsolete;
      description
        "Shutdown this instance of EIGRP";
      type empty;
    }
    container summary-metric {
      status obsolete;
      description
        "Specify summary to apply metric/filtering";
      list ipv4 {
        status obsolete;
        key "ipv4";
        leaf ipv4 {
          status obsolete;
          description
            "Summary to configure static metric";
          type inet:ipv4-address;
        }
        leaf mask {
          status obsolete;
          description
            "Network mask";
          type inet:ipv4-address;
        }
      }
      leaf A_PERIOD_B_PERIOD_C_PERIOD_D_SLASH_nn {
        status obsolete;
        description
          "Summary <network>/<length>, e.g., 192.168.0.0/16";
        type empty;
      }
    }
    container timers {
      status obsolete;
      description
        "Adjust routing timers";
      container active-time {
        status obsolete;
        description
          "time limit for active state";
        leaf atimer {
          status obsolete;
          description
            "active state time limit in minutes";
          type uint16 {
            range "1..65535";
          }
        }
        leaf disabled {
          status obsolete;
          description
            "disable time limit for active state";
          type empty;
        }
      }
      container graceful-restart {
        status obsolete;
        description
          "EIGRP Graceful Restart timer";
        leaf purge-time {
          status obsolete;
          description
            "EIGRP stale route purge time";
          type empty;
        }
      }
      container nsf {
        status obsolete;
        description
          "EIGRP NSF timer";
        leaf converge {
          status obsolete;
          description
            "EIGRP time limit for convergence after switchover";
          type empty;
        }
        leaf signal {
          status obsolete;
          description
            "EIGRP time limit for signaling NSF restart";
          type empty;
        }
      }
    }
    container traffic-share {
      status obsolete;
      description
        "How to compute traffic share over alternate paths";
      leaf balanced {
        status obsolete;
        description
          "Share inversely proportional to metric";
        type empty;
      }
      container min {
        status obsolete;
        description
          "All traffic shared among min metric paths";
        leaf across-interfaces {
          status obsolete;
          description
            "Use different interfaces for equal-cost paths";
          type empty;
        }
      }
    }
    leaf variance {
      status obsolete;
      description
        "Metric variance multiplier";
      type uint8 {
        range "1..128";
      }
    }
  }
}
