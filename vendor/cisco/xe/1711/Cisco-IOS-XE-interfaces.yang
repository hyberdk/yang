submodule Cisco-IOS-XE-interfaces {
  belongs-to Cisco-IOS-XE-native {
    prefix ios;
  }

  import cisco-semver {
    prefix cisco-semver;
  }
  import ietf-inet-types {
    prefix inet;
  }
  import Cisco-IOS-XE-types {
    prefix ios-types;
  }
  import Cisco-IOS-XE-features {
    prefix ios-features;
  }
  import Cisco-IOS-XE-interface-common {
    prefix ios-ifc;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Cisco XE Native Interfaces Yang model.
     Copyright (c) 2016-2019 by Cisco Systems, Inc.
     All rights reserved.";

  revision 2019-11-01 {
    description
      "
       - Address arp model gaps
       - Add add/except/remove options for switchport trunk allowed vlan";
    cisco-semver:module-version "2.0.0";
  }
  revision 2019-07-01 {
    description
      "- Establish semantic version baseline
       - Added support for access-session inherit disable interface-template-sticky
         and access-session inherit disable service-policy
       - Change the IPv4/IPv6 MTU range
       - Add FEC support
       - Added support for ip mask-reply
       - Fix access-session port-control type, add default value
       - Add ingress-replication bgp signaled support under nve interface
       - Add interface BD-VIF";
    cisco-semver:module-version "1.0.0";
  }
  revision 2019-03-11 {
    description
      "Modified the leafref to leaf because of pyang issue";
  }
  revision 2019-02-08 {
    description
      "Added ISIS clns commands";
  }
  revision 2019-01-27 {
    description
      "changing ingress-replication from container back to leaf to take care of backward compatibility";
  }
  revision 2019-01-24 {
    description
      "Added leaf for App-hosting Gigabit Ethernet interface";
  }
  revision 2019-01-23 {
    description
      "Removed app redundancy restriction for IF mode redundancy CLIs";
  }
  revision 2018-12-14 {
    description
      "Add AppQoE interface support";
  }
  revision 2018-12-09 {
    description
      "Add support for access-session inherit disable autoconf cli";
  }
  revision 2018-12-05 {
    description
      "Updated the Dialer interface range in line with IOS <0..255>";
  }
  revision 2018-11-16 {
    description
      "Cleanup spelling errors in description statements";
  }
  revision 2018-11-08 {
    description
      "Support Wlan-GigabitEthernet interface for ISR1K platform";
  }
  revision 2018-10-31 {
    description
      "Fix ip address annotations, remove no-address container";
  }
  revision 2018-10-23 {
    description
      "Added redundancy group and rii commands inside interface";
  }
  revision 2018-10-17 {
    description
      "Add choice for encapsulation, only one encapsulation can be set per interface";
  }
  revision 2018-10-16 {
    description
      "Added Virtual-PPP interface support";
  }
  revision 2018-09-28 {
    description
      "Changed ip vrf forwarding from type leafref to string because pyang fails";
  }
  revision 2018-09-20 {
    description
      "Corrected some description end line characters";
  }
  revision 2018-09-07 {
    description
      "Add must constraint to vrf forwaring, on vrf address-family";
  }
  revision 2018-08-29 {
    description
      "added must constraint on no ip address";
  }
  revision 2018-08-23 {
    description
      "Add cli-diff-set-after to ip-mtu to enforce the dependency on mtu";
  }
  revision 2018-08-22 {
    description
      "Add ingress-replication bgp signaled support under nve interface";
  }
  revision 2018-08-12 {
    description
      "added must constraint on ip unnumbered on interface Dialer";
  }
  revision 2018-08-06 {
    description
      "Removed switchport trunk allowed vlan leaves add/remove/except";
  }
  revision 2018-08-03 {
    description
      "Added model for port-channel load-balancing";
  }
  revision 2018-07-24 {
    description
      "Added second-dot1q under encapsulation, added presence true under dampening";
  }
  revision 2018-07-17 {
    description
      "Range specified for interface Multilink changed to uint32";
  }
  revision 2018-07-16 {
    description
      "Added vif list in interface";
  }
  revision 2018-07-11 {
    description
      "Add .* to cli-preformatted, apply input validation to disallow new lines";
  }
  revision 2018-07-10 {
    description
      "Add interface vrf forwarding downstream. Increase hold-queue size.";
  }
  revision 2018-06-28 {
    description
      "added must constraints for deleting vrf, changing to switchport from no switchport";
  }
  revision 2018-06-15 {
    description
      "Interface secondary ip address: change mandatory to incomplete command";
  }
  revision 2018-06-10 {
    description
      "SDA source templates are missing models";
  }
  revision 2018-06-06 {
    description
      "Moving switchport part to Cisco-IOS-XE-switch-isr.yang";
  }
  revision 2018-05-30 {
    description
      "Move IPv6 dhcp container to after IPv6 config to avoid dependencies";
  }
  revision 2018-05-22 {
    description
      "Change switchport trunk allowed vlan to support leaf-list";
  }
  revision 2018-05-21 {
    description
      "Interface description: change cli-suppress-quotes to cli-preformatted";
  }
  revision 2018-05-10 {
    description
      "Add 'vxlan udp port' CLI under NVE interface";
  }
  revision 2018-04-30 {
    description
      "Adding leaf node for ATM subinterface creation";
  }
  revision 2018-04-27 {
    description
      "Add presence true to 'ip virtual-reassembly'";
  }
  revision 2018-03-18 {
    description
      "Added ip address annotations for mapping of ipv4 secondary addresses";
  }
  revision 2018-03-15 {
    description
      "host-reachability protocol bgp is added under nve interface ";
  }
  revision 2018-03-06 {
    description
      "Added dependencies between mtu and ipv4/ipv6 mtu";
  }
  revision 2018-02-08 {
    description
      "Add a type of Interface: Ethernet";
  }
  revision 2017-12-14 {
    description
      "Added Change interface Cellular name pattern";
  }
  revision 2017-11-27 {
    description
      "Added Change 25GE name";
  }
  revision 2017-10-30 {
    description
      "Fix out of sync between CDB and running config for interface mop enabled";
  }
  revision 2017-09-15 {
    description
      "This revison has changes for hte new 2gig interface addition";
  }
  revision 2017-08-30 {
    description
      "Move UTD interface support";
  }
  revision 2017-08-21 {
    description
      "Add HundredGigE interface support";
  }
  revision 2017-08-16 {
    description
      "This revision has changes for new 5gig and 25gig interfaces addition";
  }
  revision 2017-08-02 {
    description
      "Added Stackwise Virtual Interface commands";
  }
  revision 2017-07-31 {
    description
      "Add dependency between ip primary and secondary";
  }
  revision 2017-07-20 {
    description
      "Change mtu range";
  }
  revision 2017-07-07 {
    description
      "Add ipv6 source-guard support and storm-control broadcast/multicast falling-threshold for int gig";
  }
  revision 2017-06-28 {
    description
      "Add nve support for special interface ucse, Ethernet-Internal and Service-Engine";
  }
  revision 2017-06-27 {
    description
      "Extend FastEthernet and FortyGigabitEthernet to allow subinterfaces";
  }
  revision 2017-06-14 {
    description
      "Add nve support for ingress-replication";
  }
  revision 2017-06-01 {
    description
      "Add dependency for interface ip address to encapsulation/dot1Q";
  }
  revision 2017-05-11 {
    description
      "fix hold-queue to allow support for both in and out queues.";
  }
  revision 2017-04-20 {
    description
      "Added ipv6/tcp/adjust-mss support, fixed loopback dampening issue, fixed ipv6 address autoconfiguration issue";
  }
  revision 2017-04-17 {
    description
      "Addition of support for group-based policy command";
  }
  revision 2017-03-24 {
    description
      "Removed bandwidth range constraints";
  }
  revision 2017-03-04 {
    description
      "Changed LISP key type to string to support OC mapping, removed Fast/Forty Ethernet pattern";
  }
  revision 2017-02-07 {
    description
      "Initial revision";
  }

  grouping nve-member-vni-mcast-group-grouping {
    container mcast-group {
      leaf multicast-group-min {
        description
          "Starting Multicast Group IPv4 Address";
        type inet:ipv4-address;
      }
      leaf multicast-group-max {
        description
          "Ending Multicast Group IPv4 Address";
        type inet:ipv4-address;
      }
    }
  }

  grouping nve-member-vni-ir-deprecated-grouping {
    leaf ingress-replication {
      status deprecated;
      description
        "Ingress Replication or Unicast mode for vni(s)";
      type inet:ipv4-address;
    }
  }

  grouping nve-member-vni-ir-group-grouping {
    container ingress-replication-config {
      description
        "Ingress Replication configuration for vni(s)";
      leaf cp-signal {
        description
          "Ingress Replication control-plane (BGP) signaling";
        type empty;
      }
      leaf-list peer-addr {
        description
          "Ingress Replication or Unicast Peer address";
        type inet:ipv4-address;
      }
    }
    uses nve-member-vni-ir-deprecated-grouping;
  }

  grouping nve-member-vni-no-grouping {
    uses nve-member-vni-ir-deprecated-grouping;
    uses nve-member-vni-mcast-group-grouping;
  }

  grouping nve-member-vni-grouping {
    uses nve-member-vni-ir-group-grouping;
    uses nve-member-vni-mcast-group-grouping;
  }

  grouping storm-control-threshold-grouping {
    container level {
      description
        "Set storm suppression level on this interface";
      container threshold {
        description
          "Broadcast address storm control";
        leaf rising-threshold {
          description
            "Enter rising threshold";
          type decimal64 {
            fraction-digits 2;
            range "0..100";
          }
        }
        leaf falling-threshold {
          description
            "Enter falling threshold";
          type decimal64 {
            fraction-digits 2;
            range "0..100";
          }
        }
      }
      container bps {
        description
          "Enter suppression level in bits per second";
        leaf rising-threshold {
          description
            "Enter rising threshold - <0.0 - 10000000000.0>[k|m|g]>";
          type ios-types:storm-control-threshold-type;
        }
        leaf falling-threshold {
          description
            "Enter falling threshold - <0.0 - 10000000000.0>[k|m|g]> ";
          type ios-types:storm-control-threshold-type;
        }
      }
      container pps {
        description
          "Enter suppression level in packets per second";
        leaf rising-threshold {
          description
            "Enter rising threshold - <0.0 - 10000000000.0>[k|m|g]";
          type ios-types:storm-control-threshold-type;
        }
        leaf falling-threshold {
          description
            "Enter falling threshold - <0.0 - 10000000000.0>[k|m|g] ";
          type ios-types:storm-control-threshold-type;
        }
      }
    }
  }

  grouping ethernet-grouping {
    choice ethernet-choice {
      leaf Ethernet {
        description
          "IEEE 802.3";
        type string;
      }
      leaf FastEthernet {
        description
          "FastEthernet IEEE 802.3";
        type string;
      }
      leaf GigabitEthernet {
        description
          "GigabitEthernet IEEE 802.3z";
        type string;
      }
      leaf FiveGigabitEthernet {
        description
          "Five Gigabit Ethernet ";
        type string;
      }
      leaf AppGigabitEthernet {
        description
          "App-hosting Gigabit Ethernet IEEE 802.3z";
        type string;
      }
      leaf Port-channel {
        description
          "Ethernet Channel of interfaces";
        type uint32;
      }
      leaf TenGigabitEthernet {
        description
          "Ten Gigabit Ethernet";
        type string;
      }
      leaf TwentyFiveGigabitEthernet {
        status obsolete;
        description
          "Twenty Five Gigabit Ethernet ";
        type string;
      }
      leaf TwentyFiveGigE {
        description
          "Twenty Five Gigabit Ethernet ";
        type string;
      }
      leaf FortyGigabitEthernet {
        description
          "Forty Gigabit Ethernet";
        type string;
      }
      leaf TwoGigabitEthernet {
        description
          "Two Gigabit Ethernet ";
        type string;
      }
      leaf HundredGigE {
        description
          "Hundred Gigabit Ethernet";
        type string;
      }
      leaf vlan {
        description
          "Catalyst Vlans";
        type uint16 {
          range "1..4094";
        }
      }
    }
  }

  grouping interface-negotiation-grouping {
    container negotiation {
      description
        "Select autonegotiation mode";
      leaf auto {
        description
          "Enable link autonegotiation";
        type boolean;
      }
    }
  }

  grouping interface-switchport-grouping {
    container switchport-wrapper {
      container switchport {
        container access {
          description
            "Set access mode characteristics of the interface";
          leaf vlan {
            description
              "Set VLAN when interface is in access mode";
            type uint16 {
              range "1..4094";
            }
          }
        }
        leaf mode {
          description
            "Set trunking mode of the interface";
          type enumeration {
            enum "access";
            enum "trunk";
          }
        }
        container trunk {
          description
            "Set trunking characteristics of the interface";
          container allowed {
            description
              "Set allowed VLAN characteristics when interface is in trunking mode";
            container vlan {
              description
                "Set allowed VLANs when interface is in trunking mode";
              choice vlan-choice {
                leaf vlans {
                  description
                    "Allow a single VLAN id (allowed value range 1-4094) 
                     or Comma-separated VLAN id range. 
                     e.g. 99 or 1-30 or  1-20,30,40-50";
                  type union {
                    type uint16 {
                      range "1..4094";
                    }
                    type string;
                  }
                }
                leaf add {
                  description
                    "VLAN IDs of the allowed VLANs when this port is in trunking mode";
                  type union {
                    type uint16 {
                      range "1..4094";
                    }
                    type string;
                  }
                }
                leaf all {
                  description
                    "all VLANs";
                  type empty;
                }
                leaf except {
                  description
                    "all VLANs except the following";
                  type union {
                    type uint16 {
                      range "1..4094";
                    }
                    type string;
                  }
                }
                leaf none {
                  description
                    "no VLANs allowed";
                  type empty;
                }
                leaf remove {
                  description
                    "VLAN IDs of disallowed VLANs when this port is in trunking mode";
                  type union {
                    type uint16 {
                      range "1..4094";
                    }
                    type string;
                  }
                }
              }
            }
          }
        }
        container native {
          leaf vlan {
            description
              "Set VLAN when interface is in access mode";
            type uint16 {
              range "1..4094";
            }
          }
        }
      }
    }
  }

  grouping interface-common-grouping {
    leaf description {
      description
        "Interface specific description";
      type string {
        pattern ".*";
        length "0..240";
      }
    }
    container switchport-conf {
      leaf switchport {
        type boolean;
      }
    }
    container switchport {
      description
        "Set switching mode characteristics";
      if-feature "ios-features:switching-platform";
    }
    container stackwise-virtual {
      description
        "Configure stackwise-virtual link values";
      leaf link {
        type uint8 {
          range "1..2";
        }
      }
      leaf dual-active-detection {
        type empty;
      }
    }
    leaf mac-address {
      description
        "Manually set interface MAC address";
      type string;
    }
    leaf shutdown {
      description
        "Shutdown the selected interface";
      type empty;
    }
    container arp {
      description
        "Set arp type (arpa, probe, snap), timeout, log options or 
         packet priority";
      leaf timeout {
        description
          "Set ARP cache timeout";
        type uint32 {
          range "0..2147483";
        }
      }
      leaf snap {
        description
          "IEEE 802.3 style arp";
        type empty;
      }
      leaf authorized {
        description
          "Only allow internal authorized ARP entry";
        type empty;
      }
      container log {
        description
          "ARP log service";
        container threshold {
          description
            "Threshold to trigger ARP log";
          leaf entries {
            description
              "Entry count to trigger ARP log";
            type uint32 {
              range "1..2147483647";
            }
          }
        }
      }
      container entries {
        description
          "ARP entries";
        container interface-limit {
          description
            "ARP Entry count Threshold";
          leaf entry-count {
            description
              "ARP Entry count Threshold";
            type uint32 {
              range "1..2147483647";
            }
          }
          leaf log {
            description
              "Rate in seconds";
            type uint32 {
              range "1..3600";
            }
          }
        }
      }
      container packet-priority {
        description
          "Set or Clear Arp Packet Priority";
        leaf enable {
          description
            "Set the Arp Packet Priority to HIGH";
          type empty;
        }
      }
    }
    container backup {
      description
        "Modify backup parameters";
      container delay {
        description
          "Delays before backup line up or down transitions";
        leaf failure {
          description
            "Seconds";
          type union {
            type uint32 {
              range "0..4294967294";
            }
            type enumeration {
              enum "never";
            }
          }
        }
        leaf secondary-disable {
          description
            "Seconds";
          type union {
            type uint32 {
              range "0..4294967294";
            }
            type enumeration {
              enum "never";
            }
          }
        }
      }
      container interface {
        description
          "Configure an interface as a backup";
        uses ios-ifc:interface-grouping;
      }
      container load {
        description
          "Load thresholds for line up or down transitions";
        leaf kickin {
          description
            "Percentage";
          type union {
            type uint32 {
              range "0..100";
            }
            type enumeration {
              enum "never";
            }
          }
        }
        leaf kickout {
          description
            "Percentage";
          type union {
            type uint32 {
              range "0..100";
            }
            type enumeration {
              enum "never";
            }
          }
        }
      }
    }
    container cemoudp {
      description
        "cemoudp";
      container reserve {
        leaf acr {
          type uint8;
        }
      }
    }
    container cws-tunnel {
      description
        "Configure Cloud Web Security Tunnel";
      leaf in {
        description
          "Inbound traffic";
        type empty;
      }
      container out {
        description
          "Out-bound traffic";
        leaf tunnel-number {
          description
            "Outbound traffic tunnel identifier";
          type uint16 {
            range "0..65534";
          }
        }
      }
    }
    container l2protocol-tunnel {
      description
        "Tunnel Layer2 protocols";
      presence "true";
      leaf cdp {
        description
          "Cisco Discovery Protocol";
        type empty;
      }
      container drop-threshold {
        description
          "Set drop threshold for protocol packets";
        leaf packet-rate {
          type uint16 {
            range "1..4096";
          }
        }
        leaf cdp {
          description
            "Cisco Discovery Protocol";
          type uint16 {
            range "1..4096";
          }
        }
        leaf stp {
          description
            "Spanning Tree Protocol";
          type uint16 {
            range "1..4096";
          }
        }
        leaf vtp {
          description
            "Vlan Trunking Protocol";
          type uint16 {
            range "1..4096";
          }
        }
      }
      container shutdown-threshold {
        description
          "Set shutdown threshold for protocol packets";
        leaf packet-rate {
          type uint16 {
            range "1..4096";
          }
        }
        leaf cdp {
          description
            "Cisco Discovery Protocol";
          type uint16 {
            range "1..4096";
          }
        }
        leaf stp {
          description
            "Spanning Tree Protocol";
          type uint16 {
            range "1..4096";
          }
        }
        leaf vtp {
          description
            "Vlan Trunking Protocol";
          type uint16 {
            range "1..4096";
          }
        }
      }
      leaf stp {
        description
          "Spanning Tree Protocol";
        type empty;
      }
      leaf vtp {
        description
          "Vlan Trunking Protocol";
        type empty;
      }
    }
    container encapsulation {
      description
        "Set encapsulation type for an interface";
      choice encap-choice {
        container dot1Q {
          description
            "IEEE 802.1Q Virtual LAN";
          leaf vlan-id {
            type uint16 {
              range "1..4094";
            }
          }
          leaf native {
            description
              "Make this as native vlan";
            type empty;
          }
          leaf second-dot1q {
            description
              "Configure this subinterface as a 1Q-in-1Q subinterface";
            type union {
              type enumeration {
                enum "any";
              }
              type string;
            }
          }
        }
        container isl {
          description
            "Inter Switch Link - Virtual LAN encapsulation";
          leaf vlan-id {
            type uint16 {
              range "1..4095";
            }
          }
        }
        container ppp {
          description
            "Point-to-Point protocol";
          presence "true";
        }
        container slip {
          description
            "Serial Line IP";
          presence "true";
        }
        container frame-relay {
          description
            "Frame Relay networks";
          presence "true";
          leaf ietf {
            description
              "Use RFC1490/RFC2427 encapsulation";
            type empty;
          }
        }
      }
    }
    container fair-queue-conf {
      leaf fair-queue {
        type boolean;
      }
    }
    container fair-queue {
      description
        "Enable Fair Queuing on an Interface";
      leaf incomplete {
        type empty;
      }
    }
    container flowcontrol {
      description
        "Configure flow operation.";
      leaf receive {
        description
          "Configure receiving flow operation";
        type enumeration {
          enum "desired";
          enum "off";
          enum "on";
        }
      }
      leaf send {
        description
          "Configure sending flow operation";
        type enumeration {
          enum "desired";
          enum "off";
          enum "on";
        }
      }
    }
    container isis {
      description
        "IS-IS commands";
    }
    container clns {
      description
        "IS-IS CLNS commands";
    }
    choice keepalive-choice {
      leaf keepalive {
        description
          "Enable keepalive";
        type boolean;
      }
      container keepalive-settings {
        container keepalive {
          description
            "Enable keepalive";
          presence "true";
          leaf period {
            type uint16 {
              range "0..32767";
            }
          }
          leaf retries {
            type uint8;
          }
        }
      }
    }
    container bfd {
      description
        "BFD interface configuration commands";
    }
    container bandwidth {
      description
        "Set bandwidth informational parameter";
      container receive {
        description
          "Specify receive-side bandwidth";
        leaf inherit {
          description
            "Specify how bandwidth is inherited";
          type empty;
        }
        leaf kilobits {
          type uint32;
        }
      }
      container inherit {
        description
          "Specify how bandwidth is inherited";
        presence "true";
        leaf kilobits {
          type uint32;
        }
      }
      leaf qos-reference {
        description
          "Reference bandwidth for QOS";
        type uint32;
      }
      leaf kilobits {
        type uint32;
      }
    }
    container dampening {
      description
        "Enable event dampening";
      presence "true";
      leaf dampening-time {
        description
          "<1-30>;;Half-life time for penalty";
        type uint16 {
          range "1..30";
        }
      }
      leaf start-reusing-time {
        description
          "<1-20000>;;Value to start reusing an interface";
        type uint16 {
          range "1..20000";
        }
      }
      leaf start-supressing-time {
        description
          "<1-20000>;;Value to start suppressing an interface";
        type uint16 {
          range "1..20000";
        }
      }
      leaf maximum-supressing-time {
        description
          "<1-255>;;Maximum duration to suppress an interface";
        type uint16 {
          range "1..255";
        }
      }
      container restart {
        description
          "Enable restart penalty";
        leaf restart {
          description
            "Enable restart penalty";
          type empty;
        }
        leaf restart-penalty {
          description
            "<1-20000>;;Penalty applied at restart";
          type uint16 {
            range "1..20000";
          }
        }
      }
    }
    leaf if-state {
      type enumeration {
        enum "nhrp";
      }
    }
    leaf delay {
      description
        "Specify interface throughput delay";
      type uint32 {
        range "1..16777215";
      }
    }
    container domain {
      description
        "Specify a domain";
      leaf name {
        type string;
      }
      leaf path {
        description
          "Specify a service provider for this interface";
        type string;
      }
      leaf internet-bound {
        description
          "Specify Internet-bound interface";
        type empty;
      }
      leaf path-id {
        description
          "Specify service provider path-id for this interface";
        type uint8;
      }
      leaf path-last-resort {
        description
          "Specify if you want this interface to be a path of last resort";
        type empty;
      }
      leaf zero-sla {
        description
          "Specify if you want this interface to be a 0-sla interface";
        type empty;
      }
    }
    list hold-queue {
      description
        "Set hold queue depth";
      key "direction";
      leaf direction {
        type enumeration {
          enum "in";
          enum "out";
        }
      }
      leaf queue-length {
        type uint32 {
          range "0..240000";
        }
      }
    }
    container mpls;
    choice vrf-choice {
      container ip-vrf {
        container ip {
          container vrf {
            leaf forwarding {
              description
                "Configure forwarding table";
              type string;
            }
          }
        }
      }
      container vrf {
        description
          "VPN Routing/Forwarding parameters on the interface";
        leaf forwarding {
          description
            "Configure forwarding table";
          must "/ios:native/ios:vrf/ios:definition[ios:name=current()]" {
            error-message "VRF must be created 1st, deleted last";
          }
          must "not(../../ip/address) or /ios:native/ios:vrf/ios:definition[ios:name=current()]/ios:address-family/ios:ipv4" {
            error-message "Address-family ipv4 in VRF must be created 1st, deleted last";
          }
          must "not (../../switchport-conf/switchport) or (../../switchport-conf/switchport = 'false')" {
            error-message "To configure vrf forwarding, set switchport to false 1st; To change switchport from false to true, delete vrf forwarding 1st";
          }
          type string;
        }
        leaf downstream {
          description
            "Configure different VRF for downstream traffic";
          when "../forwarding";
          must "/ios:native/ios:vrf/ios:definition[ios:name=current()]" {
            error-message "VRF must be created 1st, deleted last";
          }
          type string;
        }
      }
    }
    container ip {
      description
        "Interface Internet Protocol config commands";
      leaf admission {
        description
          "Apply Network Admission Control";
        type string;
      }
      container access-group {
        description
          "Specify access control for packets";
        container in {
          choice apply-type {
            case apply-common {
              container common-acl {
                leaf common {
                  description
                    "specify ipv4 common ACL for packet filtering";
                  type ios-types:exp-acl-type;
                  mandatory true;
                }
                leaf in {
                  description
                    "inbound packets";
                  type empty;
                }
              }
            }
            case apply-intf {
              container acl {
                leaf acl-name {
                  type ios-types:exp-acl-type;
                  mandatory true;
                }
                leaf in {
                  description
                    "inbound packets";
                  type empty;
                }
              }
            }
          }
        }
        container out {
          choice apply-type {
            case apply-common {
              container common-acl {
                leaf common {
                  description
                    "specify ipv4 common ACL for packet filtering";
                  type ios-types:exp-acl-type;
                  mandatory true;
                }
                leaf out {
                  description
                    "outbound packets";
                  type empty;
                }
              }
            }
            case apply-intf {
              container acl {
                leaf acl-name {
                  type ios-types:exp-acl-type;
                  mandatory true;
                }
                leaf out {
                  description
                    "outbound packets";
                  type empty;
                }
              }
            }
          }
        }
      }
      container arp {
        description
          "Configure ARP features";
        container inspection {
          description
            "Arp Inspection configuration";
          container limit {
            description
              "Configure Rate limit of incoming ARP packets";
            leaf none {
              description
                "No limit";
              type empty;
            }
            leaf rate {
              description
                "Rate Limit";
              type uint32;
            }
          }
          leaf trust {
            description
              "Configure Trust state";
            type empty;
          }
        }
      }
      container vrf {
        description
          "VPN Routing/Forwarding parameters on the interface";
        leaf receive {
          description
            "Add Interface Address into VRF Table";
          type string;
        }
        leaf sitemap {
          description
            "Configure route-map for routesreceived from this site";
          type string;
        }
        container forwarding {
          description
            "Configure forwarding table";
          leaf Liin-vrf {
            type empty;
          }
          leaf mgmtVrf {
            type empty;
          }
          leaf word {
            type string;
          }
        }
      }
      choice address-choice {
        leaf unnumbered {
          description
            "Enable IP processing without an explicit address";
          must "starts-with(., 'Dialer') and  (number(substring-after(., 'Dialer')) = /ios:native/ios:interface/ios:Dialer/ios:name) or not (starts-with(., 'Dialer'))" {
            error-message "To use a Dialer interface, the Dialer interface has to be configured 1st, vice versa for delete";
          }
          type string;
        }
        container address {
          description
            "Set the IP address of an interface";
          choice address-choice {
            case fixed-case {
              list secondary {
                key "address";
                leaf address {
                  type inet:ipv4-address;
                }
                leaf mask {
                  mandatory true;
                  type inet:ipv4-address;
                }
                leaf secondary {
                  description
                    "Make this IP address a secondary address.
                     This leaf must be set in order to prevent it from overriding 
                     the primary address";
                  mandatory true;
                  type empty;
                }
              }
              container primary {
                leaf address {
                  must "not (../../../../switchport-conf/switchport) or (../../../../switchport-conf/switchport = 'false')" {
                    error-message "To configure ip address, set switchport to false 1st; To change switchport from false to true, delete ip address 1st";
                  }
                  type inet:ipv4-address;
                }
                leaf mask {
                  type inet:ipv4-address;
                }
              }
            }
            case dhcp-case {
              container dhcp {
                description
                  "IP Address negotiated via DHCP";
                presence "IP Address negotiated via DHCP";
                container client-id {
                  description
                    "Specify client-id to use";
                  uses ethernet-grouping;
                }
                leaf hostname {
                  description
                    "Specify value for hostname option";
                  type string;
                }
              }
            }
            case negotiated-case {
              leaf negotiated {
                description
                  "IP Address negotiated via IKEv2 Modeconfig";
                type empty;
              }
            }
          }
        }
      }
      container directed-broadcast {
        description
          "Enable forwarding of directed broadcasts";
        presence "true";
        leaf direct-broadcast {
          type ios-types:exp-acl-type;
        }
      }
      container hello-interval {
        status obsolete;
        description
          "Configures EIGRP-IPv4 hello interval";
        leaf eigrp {
          status obsolete;
          description
            "Enhanced Interior Gateway Routing Protocol (EIGRP)";
          type uint16;
        }
        leaf seconds {
          status obsolete;
          description
            "Seconds between hello transmissions";
          type uint16;
        }
      }
      container authentication {
        status obsolete;
        description
          "authentication subcommands";
        container key-chain {
          status obsolete;
          description
            "key-chain";
          leaf eigrp {
            status obsolete;
            description
              "Enhanced Interior Gateway Routing Protocol (EIGRP)";
            type uint16;
          }
          leaf name {
            status obsolete;
            description
              "name of key-chain";
            type string;
          }
        }
        container mode {
          status obsolete;
          description
            "mode";
          leaf eigrp {
            status obsolete;
            description
              "Enhanced Interior Gateway Routing Protocol (EIGRP)";
            type uint16;
          }
          leaf md5 {
            status obsolete;
            description
              "Keyed message digest";
            type empty;
          }
        }
      }
      container hold-time {
        status obsolete;
        description
          "Configures EIGRP-IPv4 hold time";
        leaf eigrp {
          status obsolete;
          description
            "Enhanced Interior Gateway Routing Protocol (EIGRP)";
          type uint16;
        }
        leaf seconds {
          status obsolete;
          description
            "Seconds before neighbor is considered down";
          type uint16;
        }
      }
      list helper-address {
        description
          "Specify a destination address for UDP broadcasts";
        key "address";
        leaf address {
          type inet:ipv4-address;
        }
        choice helper-choice {
          leaf global {
            description
              "Helper-address is global";
            type empty;
          }
          leaf vrf {
            description
              "VRF name for helper-address (if different from interface VRF)";
            must "/ios:native/ios:vrf/ios:definition[ios:name=current()] or /ios:native/ios:ip/ios:vrf[ios:name=current()]" {
              error-message "VRF must be created 1st, deleted last";
            }
            type string;
          }
        }
      }
      container pim {
        description
          "PIM interface commands";
      }
      container policy {
        description
          "Enable policy routing";
        leaf route-map {
          description
            "Policy route-map";
          type string;
        }
      }
      leaf local-proxy-arp {
        description
          "Enable local-proxy ARP";
        type empty;
      }
      leaf proxy-arp {
        description
          "Enable proxy ARP";
        type boolean;
      }
      container rip {
        description
          "Router Information Protocol";
        container authentication {
          description
            "Authentication control";
          leaf key-chain {
            description
              "Authentication key-chain";
            type string;
          }
          container mode {
            description
              "Authentication mode";
            leaf md5 {
              description
                "Keyed message digest";
              type empty;
            }
            leaf text {
              description
                "Clear text authentication";
              type empty;
            }
          }
        }
      }
      container route-cache-conf {
        leaf route-cache {
          type boolean;
        }
      }
      container route-cache {
        description
          "Enable fast-switching cache for outgoing packets";
        presence "true";
        leaf cef {
          description
            "Enable Cisco Express Forwarding";
          type boolean;
        }
        leaf flow {
          description
            "Enable Flow fast-switching cache";
          type boolean;
        }
        leaf policy {
          description
            "Enable fast-switching policy cache for outgoing packets";
          type boolean;
        }
        leaf same-interface {
          description
            "Enable fast-switching on the same interface";
          type boolean;
        }
      }
      container router {
        description
          "IP router interface commands";
      }
      leaf redirects {
        description
          "Enable sending ICMP Redirect messages";
        type boolean;
      }
      leaf mask-reply {
        description
          "Enable sending ICMP Mask Reply messages";
        type empty;
      }
      container tcp {
        description
          "TCP header compression and other parameters";
        leaf adjust-mss {
          description
            "Adjust the mss of transit packets";
          type uint16 {
            range "500..1460";
          }
        }
      }
      container virtual-reassembly {
        presence "true";
        leaf max-reassemblies {
          type uint32;
        }
        leaf max-fragments {
          type uint32;
        }
        leaf timeout {
          type uint32;
        }
        leaf drop-fragments {
          type empty;
        }
        leaf in {
          type empty;
        }
      }
      container dhcp {
        description
          "Configure DHCP parameters for this interface";
      }
      leaf mtu {
        description
          "Set IP Maximum Transmission Unit";
        type uint16 {
          range "68..9976";
        }
      }
      leaf mroute-cache {
        description
          "Enable switching cache for incoming multicast packets";
        type boolean;
      }
      container summary-address {
        list eigrp {
          status obsolete;
          description
            "Enhanced Interior Gateway Routing Protocol (EIGRP)";
          key "id";
          leaf id {
            status obsolete;
            type string;
          }
          leaf ip {
            status obsolete;
            type inet:ipv4-address;
          }
          leaf mask {
            status obsolete;
            type inet:ipv4-address;
          }
          leaf metric {
            status obsolete;
            type uint32;
          }
        }
      }
      container verify {
        description
          "Enable per packet validation";
        container source {
          description
            "Validation of source address";
          presence "true";
          container vlan {
            description
              "vlan specification";
            container dhcp-snooping {
              description
                "snooping enable vlan";
              presence "true";
              leaf port-security {
                description
                  "port security";
                type empty;
              }
            }
          }
        }
        container unicast {
          description
            "Enable per packet validation for unicast";
          container reverse-path {
            description
              "Reverse path validation of source address (old command format)";
            presence "true";
          }
          container source {
            description
              "Validation of source address";
            leaf reachable-via {
              description
                "Specify reachability check to apply to the source address";
              type enumeration {
                enum "any";
                enum "rx";
              }
            }
            leaf allow-self-ping {
              description
                "Allow router to ping itself (opens vulnerability in verification)";
              type empty;
            }
            leaf allow-default {
              description
                "Allow default route to match when checking source address";
              type empty;
            }
          }
        }
      }
    }
    container ipv6 {
      description
        "IPv6 interface subcommands";
      container destination-guard {
        description
          "Configure ipv6 destination guard on the interface";
        presence "true";
        leaf attach-policy {
          description
            "Apply a policy for feature ipv6 destguard";
          type string;
        }
      }
      container source-guard {
        description
          "Configure ipv6 source guard on the interface";
        presence "true";
        leaf attach-policy {
          description
            "Apply a policy for feature ipv6 sourceguard";
          type string;
        }
      }
      container dhcp {
        description
          "IPv6 DHCP interface subcommands";
      }
      container address {
        description
          "Configure IPv6 address on interface";
        container dhcp {
          description
            "Obtain IPv6 address from DHCP server";
          presence "true";
          leaf rapid-commit {
            description
              "rapid-commit for prefix delegation";
            type empty;
          }
        }
        container autoconfig {
          description
            "Obtain address using autoconfiguration";
          presence "true";
          leaf default {
            description
              "Insert default route";
            type empty;
          }
        }
        list prefix-list {
          key "prefix";
          leaf prefix {
            type ios-types:ipv6-prefix;
          }
          leaf anycast {
            description
              "Configure as an anycast";
            type empty;
          }
          leaf eui-64 {
            description
              "Use eui-64 interface identifier";
            type empty;
          }
        }
        list link-local-address {
          key "address";
          leaf address {
            type inet:ipv6-address;
          }
          leaf link-local {
            description
              "Use link-local address";
            type empty;
          }
        }
      }
      leaf unnumbered {
        description
          "Preferred interface for source address selection";
        type string;
      }
      leaf enable {
        description
          "Enable IPv6 on interface";
        type empty;
      }
      leaf mtu {
        description
          "Set IPv6 Maximum Transmission Unit";
        type uint16 {
          range "1280..9976";
        }
      }
      container nd {
        description
          "IPv6 interface Neighbor Discovery subcommands";
      }
      container router {
        description
          "IPv6 router interface commands";
      }
      leaf redirects {
        description
          "Enable sending ICMP Redirect messages";
        type boolean;
      }
      container tcp {
        description
          "TCP header compression and other parameters";
        leaf adjust-mss {
          description
            "Adjust the mss of transit packets";
          type uint16 {
            range "40..1454";
          }
        }
      }
      list traffic-filter {
        description
          "Access control list for packets";
        key "direction";
        leaf direction {
          type enumeration {
            enum "in";
            enum "out";
          }
        }
        leaf access-list {
          type string;
        }
      }
    }
    leaf load-interval {
      description
        "Specify interval for load calculation for an interface";
      type uint16 {
        range "0..600";
      }
    }
    container logging {
      description
        "Configure logging for interface";
      container event {
        description
          "Interface events";
        leaf bundle-status {
          description
            "BUNDLE/UNBUNDLE messages";
          type empty;
        }
        leaf link-status {
          description
            "UPDOWN and CHANGE messages";
          type empty;
        }
        leaf trunk-status {
          description
            "TRUNK status messages";
          type empty;
        }
        leaf nfas-status {
          description
            "NFAS D-channel status messages";
          type empty;
        }
        leaf power-inline-status {
          description
            "Inline power messages";
          type empty;
        }
        leaf status {
          description
            "Spanning-tree state change messages";
          type empty;
        }
        container spanning-tree {
          description
            "Spanning-tree Interface events";
          presence "true";
          leaf status {
            description
              "Spanning-tree state change messages";
            type empty;
          }
        }
        container subif-link-status {
          description
            "Sub-interface UPDOWN and CHANGE messages";
          presence "true";
          leaf ignore-bulk {
            description
              "Do not log messages when the main interface is transitioning";
            type empty;
          }
        }
      }
    }
    container mdix {
      description
        "Set Media Dependent Interface with Crossover";
      leaf auto {
        type boolean;
      }
    }
    container mop {
      leaf enabled {
        type boolean;
      }
      leaf sysid {
        description
          "Send out MOP periodic system ID messages";
        type boolean;
      }
    }
    leaf max-reserved-bandwidth {
      description
        "Maximum Reservable Bandwidth on an Interface";
      type uint8 {
        range "1..100";
      }
    }
    leaf mtu {
      description
        "Set the interface Maximum Transmission Unit (MTU)";
      type uint16 {
        range "64..18000";
      }
    }
    container interface_qos {
      container trust {
        leaf device {
          type enumeration {
            enum "cisco-phone";
          }
        }
      }
    }

    grouping rg-exclusive-decrement-options {
      leaf exclusive {
        description
          "Exclusive";
        type empty;
      }
      leaf decrement-last {
        description
          "Specify decrement value";
        type uint8 {
          range "1..255";
        }
      }
    }
    container redundancy {
      description
        "RG redundancy interface config";
      list group {
        description
          "RG redundancy traffic interface config";
        key "id";
        leaf id {
          description
            "RG Group Id";
          type uint8 {
            range "1..2";
          }
          must "../../rii/id" {
            error-message "Configure RII first and unconfigure it last";
          }
        }
        choice rg-choice {
          case decrement-case {
            leaf decrement {
              description
                "Specify decrement value";
              type uint8 {
                range "1..255";
              }
            }
          }
          case ip-case {
            list virtual-ip {
              description
                "Virtual-IP address family";
              key "ip-family";
              leaf ip-family {
                description
                  "IP Address family";
                type enumeration {
                  enum "ip";
                  enum "ipv6";
                }
              }
              container ipv4-address {
                description
                  "IPv4 Address";
                when "../ip-family = 'ip'";
                leaf ip {
                  type inet:ipv4-address;
                }
                uses rg-exclusive-decrement-options;
              }
              container ipv6-address {
                description
                  "IPv6 Address";
                when "../ip-family = 'ipv6'";
                leaf ipv6-prefix {
                  type ios-types:ipv6-prefix;
                }
                uses rg-exclusive-decrement-options;
              }
            }
          }
        }
      }
      container rii {
        description
          "Redundancy interface identifier id for the RG";
        leaf id {
          type uint16 {
            range "1..65535";
          }
        }
        leaf decrement {
          description
            "Specify decrement value. This operation changes the decrement value of all configured groups";
          type uint8 {
            range "1..255";
          }
        }
      }
    }
    leaf service-insertion {
      description
        "Service-insertion AppNav Controller";
      type enumeration {
        enum "waas";
        enum "appqoe";
      }
    }
    container source {
      description
        "Get config from another source";
      container template {
        description
          "Get config from a template";
        list template-name {
          ordered-by user;
          key "template-name";
          leaf template-name {
            type string;
          }
          leaf merge {
            description
              "merge option of binding";
            type empty;
          }
        }
      }
    }
    container standby {
      description
        "HSRP interface configuration commands";
      leaf version {
        description
          "HSRP version";
        type enumeration {
          enum "1";
          enum "2";
        }
      }
      leaf bfd {
        description
          "Enable HSRP BFD";
        type empty;
      }
      container delay {
        description
          "HSRP initialisation delay";
        leaf minimum {
          description
            "Minimum delay";
          type uint16 {
            range "0..10000";
          }
        }
        leaf reload {
          description
            "Delay after reload";
          type uint16 {
            range "0..10000";
          }
        }
      }
      leaf mac-refresh {
        description
          "Refresh MAC cache on switch by periodically sending packet from virtual mac address";
        type uint8 {
          range "0..255";
        }
      }
      container use-bia {
        description
          "HSRP uses interface's burned in address";
        presence "true";
        container scope {
          description
            "Specify the scope of use-bia";
          leaf interface {
            description
              "Use-bia applies to all groups on this interface or sub-interface";
            type empty;
          }
        }
      }
      list standby-list {
        key "group-number";
        leaf group-number {
          type uint16;
        }
        container authentication {
          description
            "Authentication";
          choice auth {
            leaf word {
              type string;
            }
            container md5 {
              description
                "Use MD5 authentication";
              leaf key-chain {
                description
                  "Set key chain";
                type string;
              }
              container key-string {
                description
                  "Set key string";
                leaf encrypt {
                  type enumeration {
                    enum "0";
                    enum "7";
                  }
                }
                leaf string {
                  type string;
                }
                leaf timeout {
                  description
                    "Set timeout";
                  type uint16 {
                    range "0..32767";
                  }
                }
              }
            }
            leaf text {
              description
                "Plain text authentication";
              type string;
            }
          }
        }
        leaf follow {
          description
            "Name of HSRP group to follow";
          type string;
        }
        container ip {
          description
            "Enable HSRP and set the virtual IP address";
          presence "true";
          leaf address {
            type inet:ipv4-address;
          }
          leaf secondary {
            description
              "Make this IP address a secondary virtual IP address";
            type empty;
          }
        }
        leaf ipv6 {
          description
            "Enable HSRP IPv6";
          type union {
            type inet:ipv6-address;
            type ios-types:ipv6-prefix;
            type enumeration {
              enum "autoconfig";
            }
          }
        }
        leaf mac-address {
          description
            "Virtual MAC address";
          type string;
        }
        leaf name {
          description
            "Redundancy name string";
          type string;
        }
        container preempt {
          description
            "Overthrow lower priority Active routers";
          presence "true";
          container delay {
            description
              "Wait before preempting";
            leaf minimum {
              description
                "Delay at least this long";
              type uint16 {
                range "0..3600";
              }
            }
            leaf reload {
              description
                "Delay after reload";
              type uint16 {
                range "0..3600";
              }
            }
            leaf sync {
              description
                "Wait for IP redundancy client";
              type uint16 {
                range "0..3600";
              }
            }
          }
        }
        leaf priority {
          description
            "Priority level";
          type uint8;
        }
        container redirect {
          description
            "Configure sending of ICMP Redirect messages with an HSRP virtual IP address as the gateway IP address";
          container advertisement {
            description
              "Redirect advertisement messages";
            container authentication {
              description
                "Authentication";
              container md5 {
                description
                  "Use MD5 authentication";
                leaf key-chain {
                  description
                    "Set key chain";
                  type string;
                }
                container key-string {
                  description
                    "Set key string";
                  leaf encrypt {
                    type enumeration {
                      enum "0";
                      enum "7";
                    }
                  }
                  leaf string {
                    type string;
                  }
                  leaf timeout {
                    description
                      "Set timeout";
                    type uint16 {
                      range "0..32767";
                    }
                  }
                }
              }
            }
          }
          container timers {
            description
              "Adjust redirect timers";
            leaf advertisement {
              type uint16 {
                range "10..180";
              }
            }
            leaf holddown {
              type uint16 {
                range "30..3600";
              }
            }
          }
          leaf unknown {
            description
              "Redirect to non-HSRP routers";
            type empty;
          }
        }
        container timers {
          description
            "Hello and hold timers";
          container hello-interval {
            choice hello-interval-choice {
              leaf seconds {
                type uint8 {
                  range "1..254";
                }
              }
              leaf msec {
                description
                  "Specify hello interval in milliseconds";
                type uint16 {
                  range "15..999";
                }
              }
            }
          }
          container hold-time {
            choice hold-time-choice {
              leaf seconds {
                type uint8 {
                  range "1..255";
                }
              }
              leaf msec {
                description
                  "Specify hold time in milliseconds";
                type uint16 {
                  range "50..3000";
                }
              }
            }
          }
        }
        list track {
          description
            "Priority tracking";
          key "number";
          leaf number {
            type uint16 {
              range "1..1000";
            }
          }
          leaf decrement {
            description
              "Priority decrement";
            type uint8;
          }
          leaf shutdown {
            description
              "Shutdown group";
            type empty;
          }
        }
      }
    }
    container access-session {
      description
        "Access Session specific Interface Configuration Commands";
      leaf closed {
        description
          "Enable closed access on port (disabled by default, i.e. open access)";
        type empty;
      }
      leaf port-control-config {
        description
          "Set the port-control value";
        type enumeration {
          enum "auto";
          enum "force-authorized";
          enum "force-unauthorized";
        }
        default "force-authorized";
      }
      container port-control {
        status obsolete;
        description
          "Set the port-control value. DEPRECATED, use port-control-config instead";
        leaf auto {
          status obsolete;
          description
            "PortState set to automatic";
          type empty;
        }
      }
      leaf control-direction-config {
        description
          "Set the control-direction on the interface";
        type enumeration {
          enum "both";
          enum "in";
        }
        default "both";
      }
      container control-direction {
        status obsolete;
        description
          "Set the control-direction on the interface (DEPRECATED, use control-direction-config)";
        leaf in {
          status obsolete;
          description
            "Control inbound traffic only";
          type empty;
        }
      }
      leaf host-mode {
        description
          "Set the Host mode for authentication on this interface";
        type enumeration {
          enum "multi-auth";
          enum "multi-domain";
          enum "multi-host";
          enum "single-host";
        }
        default "multi-auth";
      }
      container inherit {
        description
          "Access Session Inherit";
        container disable {
          description
            "Access Session disable";
          leaf autoconf {
            description
              "Auto Conf";
            type empty;
          }
          leaf interface-template-sticky {
            description
              "Interface Template Sticky";
            type empty;
          }
          leaf service-policy {
            description
              "Service Policy";
            type empty;
          }
        }
      }
      leaf monitor {
        description
          "Apply interface defined access-session monitor";
        type boolean;
        default "true";
      }
      container interface-template {
        description
          "Set the local interface-template sticky";
        container sticky {
          description
            "Interface templates set to sticky";
          presence "true";
          leaf timer {
            description
              "Sticky timer value";
            type uint16 {
              range "1..65535";
            }
          }
        }
      }
    }
    container storm-control {
      description
        "storm configuration";
      container action {
        description
          "Action to take for storm..control;";
        leaf level {
          description
            "Set storm suppression level on this interface";
          type decimal64 {
            fraction-digits 2;
            range "0..100";
          }
        }
        leaf shutdown {
          description
            "Shutdown this interface if a storm occurs";
          type empty;
        }
        leaf trap {
          description
            "Send SNMP trap if a storm occurs";
          type empty;
        }
      }
      container broadcast {
        description
          "Broadcast address storm control";
        container include {
          leaf multicast {
            type empty;
          }
        }
        uses storm-control-threshold-grouping;
      }
      container multicast {
        description
          "Multicast address storm control";
        uses storm-control-threshold-grouping;
      }
      container unicast {
        description
          "Unicast address storm control";
        uses storm-control-threshold-grouping;
      }
      container unknown-unicast {
        description
          "Unknown-Unicast address storm control";
        uses storm-control-threshold-grouping;
      }
    }
    container subscriber {
      description
        "Subscriber inactivity timeout value.";
      container aging {
        description
          "Obtain inactivity timeout value from the server";
        choice timer-probe {
          container inactivity-timer {
            description
              "Inactivity timeout value";
            leaf value {
              description
                "Enter a value between 1 and 65535 in seconds";
              type uint16 {
                range "1..65535";
              }
            }
            leaf probe {
              description
                "ARP probe";
              type empty;
            }
          }
          leaf probe {
            description
              "ARP probe";
            type empty;
          }
        }
      }
    }
    container trust {
      description
        "Set trust value for the interface";
      leaf device {
        description
          "trusted device class";
        type enumeration {
          enum "cisco-phone";
          enum "cts";
          enum "ip-camera";
          enum "media-player";
        }
      }
    }
    container priority-queue {
      description
        "Configure priority scheduling";
      container cos-map {
        description
          "Configure cos-map for a queue";
        leaf id {
          type uint8;
        }
        leaf-list cos-values {
          max-elements "8";
          type uint8 {
            range "0..7";
          }
        }
      }
      leaf out {
        description
          "egress priority queue";
        type empty;
      }
    }
    container rcv-queue {
      description
        "Configure receive queue(s)";
      list cos-map {
        description
          "Configure cos-map for a queue threshold";
        key "queue-id threshold-id";
        leaf queue-id {
          type uint8 {
            range "1..3";
          }
        }
        leaf threshold-id {
          type uint8 {
            range "1..8";
          }
        }
        leaf-list cos-values {
          max-elements "8";
          type uint8 {
            range "0..7";
          }
        }
      }
    }
    container peer {
      description
        "Peer parameters for point to point interfaces";
      container default {
        description
          "Specify default parameters";
        container ip {
          description
            "Specify default IP parameters";
          container address {
            description
              "Specify default IP address";
            choice address-choice {
              leaf dhcp {
                description
                  "Use DHCP proxy client mechanism to allocate a peer IP address";
                type empty;
              }
              container dhcp-pool {
                description
                  "Use local DHCP pools to allocate a peer IP address";
                presence "true";
                leaf pools {
                  type string;
                }
              }
              container pool {
                description
                  "Use IP pool mechanism to allocate a peer IP address";
                presence "true";
                leaf pools {
                  type string;
                }
              }
            }
          }
        }
      }
    }
    container pm-path {
      description
        "Global pm-path configuration";
      leaf name {
        description
          "WORD Path name";
        type string;
      }
      leaf interface-id {
        description
          "<1-255> Specify the interface-id value";
        type uint8 {
          range "1..255";
        }
      }
    }
  }

  grouping interface-with-dependency-grouping {
    choice interface-choice {
      leaf AppNav-Compress {
        description
          "Service-Context Virtual Interface Compress";
        type leafref {
          path "/ios:native/ios:interface/ios:AppNav-Compress/ios:name";
        }
      }
      leaf AppNav-UnCompress {
        description
          "Service-Context Virtual Interface UnCompress";
        type leafref {
          path "/ios:native/ios:interface/ios:AppNav-UnCompress/ios:name";
        }
      }
      leaf ATM {
        description
          "ATM interface";
        type leafref {
          path "/ios:native/ios:interface/ios:ATM/ios:name";
        }
      }
      container ATM-subinterface {
        leaf ATM {
          type leafref {
            path "/ios:native/ios:interface/ios:ATM-subinterface/ios:ATM/ios:name";
          }
        }
      }
      leaf ATM-ACR {
        description
          "ATM-ACR interface";
        type leafref {
          path "/ios:native/ios:interface/ios:ATM-ACR/ios:name";
        }
      }
      container ATM-ACRsubinterface {
        leaf ATM-ACR {
          type leafref {
            path "/ios:native/ios:interface/ios:ATM-ACRsubinterface/ios:ATM-ACR/ios:name";
          }
        }
      }
      leaf BDI {
        description
          "Bridge-Domain interface";
        type leafref {
          path "/ios:native/ios:interface/ios:BDI/ios:name";
        }
      }
      leaf CEM {
        description
          "CEM interface";
        type leafref {
          path "/ios:native/ios:interface/ios:CEM/ios:name";
        }
      }
      leaf CEM-ACR {
        description
          "CEM-ACR interface";
        type leafref {
          path "/ios:native/ios:interface/ios:CEM-ACR/ios:name";
        }
      }
      leaf Embedded-Service-Engine {
        description
          "cisco embedded service engine module";
        type leafref {
          path "/ios:native/ios:interface/ios:Embedded-Service-Engine/ios:name";
        }
      }
      leaf Ethernet {
        description
          "IEEE 802.3";
        type leafref {
          path "/ios:native/ios:interface/ios:Ethernet/ios:name";
        }
      }
      leaf FastEthernet {
        description
          "FastEthernet IEEE 802.3";
        type leafref {
          path "/ios:native/ios:interface/ios:FastEthernet/ios:name";
        }
      }
      leaf GigabitEthernet {
        description
          "GigabitEthernet IEEE 802.3z";
        type leafref {
          path "/ios:native/ios:interface/ios:GigabitEthernet/ios:name";
        }
      }
      leaf FiveGigabitEthernet {
        description
          "Five GigabitEthernet ";
        type leafref {
          path "/ios:native/ios:interface/ios:FiveGigabitEthernet/ios:name";
        }
      }
      leaf AppGigabitEthernet {
        description
          "App-hosting Gigabit Ethernet IEEE 802.3z";
        type leafref {
          path "/ios:native/ios:interface/ios:AppGigabitEthernet/ios:name";
        }
      }
      leaf TwentyFiveGigE {
        description
          "Twenty Five GigabitEthernet ";
        type leafref {
          path "/ios:native/ios:interface/ios:TwentyFiveGigE/ios:name";
        }
      }
      leaf TwoGigabitEthernet {
        description
          "Two GigabitEthernet ";
        type leafref {
          path "/ios:native/ios:interface/ios:TwoGigabitEthernet/ios:name";
        }
      }
      leaf FortyGigabitEthernet {
        description
          "Forty GigabitEthernet ";
        type leafref {
          path "/ios:native/ios:interface/ios:FortyGigabitEthernet/ios:name";
        }
      }
      leaf HundredGigE {
        description
          "Hundred GigabitEthernet";
        type leafref {
          path "/ios:native/ios:interface/ios:HundredGigE/ios:name";
        }
      }
      leaf LISP {
        description
          "Locator/ID Separation Protocol Virtual Interface";
        type leafref {
          path "/ios:native/ios:interface/ios:LISP/ios:name";
        }
      }
      container LISP-subinterface {
        description
          "Locator/ID Separation Protocol Virtual Interface";
        leaf LISP {
          type leafref {
            path "/ios:native/ios:interface/ios:LISP-subinterface/ios:LISP/ios:name";
          }
        }
      }
      leaf Loopback {
        description
          "Loopback interface";
        type leafref {
          path "/ios:native/ios:interface/ios:Loopback/ios:name";
        }
      }
      leaf Multilink {
        description
          "Multilink-group interface";
        type leafref {
          path "/ios:native/ios:interface/ios:Multilink/ios:name";
        }
      }
      leaf nve {
        description
          "Network virtualization endpoint interface";
        type leafref {
          path "/ios:native/ios:interface/ios:nve/ios:name";
        }
      }
      leaf overlay {
        description
          "Overlay interface";
        type leafref {
          path "/ios:native/ios:interface/ios:overlay/ios:name";
        }
      }
      leaf Port-channel {
        description
          "Ethernet Channel of interfaces";
        type leafref {
          path "/ios:native/ios:interface/ios:Port-channel/ios:name";
        }
      }
      container Port-channel-subinterface {
        leaf Port-channel {
          type leafref {
            path "/ios:native/ios:interface/ios:Port-channel-subinterface/ios:Port-channel/ios:name";
          }
        }
      }
      leaf pseudowire {
        description
          "Pseudowire Interface";
        type leafref {
          path "/ios:native/ios:interface/ios:pseudowire/ios:name";
        }
      }
      leaf SM {
        description
          "SM Interface";
        type leafref {
          path "/ios:native/ios:interface/ios:SM/ios:name";
        }
      }
      leaf Cellular {
        description
          "Cellular Interface";
        type leafref {
          path "/ios:native/ios:interface/ios:Cellular/ios:name";
        }
      }
      leaf Dialer {
        description
          "Dialer Interface";
        type leafref {
          path "/ios:native/ios:interface/ios:Dialer/ios:name";
        }
      }
      leaf Serial {
        description
          "Serial interface";
        type leafref {
          path "/ios:native/ios:interface/ios:Serial/ios:name";
        }
      }
      leaf Async {
        description
          "Async serial interface";
        type leafref {
          path "/ios:native/ios:interface/ios:Async/ios:name";
        }
      }
      leaf TenGigabitEthernet {
        description
          "Ten Gigabit Ethernet";
        type leafref {
          path "/ios:native/ios:interface/ios:TenGigabitEthernet/ios:name";
        }
      }
      leaf Tunnel {
        description
          "Tunnel interface";
        type leafref {
          path "/ios:native/ios:interface/ios:Tunnel/ios:name";
        }
      }
      leaf Virtual-Template {
        description
          "Virtual Template interface";
        type leafref {
          path "/ios:native/ios:interface/ios:Virtual-Template/ios:name";
        }
      }
      leaf Vlan {
        description
          "Iosxr Vlans";
        type leafref {
          path "/ios:native/ios:interface/ios:Vlan/ios:name";
        }
      }
      leaf VirtualPortGroup {
        description
          "Virtual Port Group";
        type leafref {
          path "/ios:native/ios:interface/ios:VirtualPortGroup/ios:name";
        }
      }
      leaf vasileft {
        description
          "vasileft";
        type leafref {
          path "/ios:native/ios:interface/ios:vasileft/ios:name";
        }
      }
      leaf vasiright {
        description
          "vasiright";
        type leafref {
          path "/ios:native/ios:interface/ios:vasiright/ios:name";
        }
      }
      leaf BD-VIF {
        description
          "Bridge-Domain Virtual IP interface";
        type leafref {
          path "/ios:native/ios:interface/ios:BD-VIF/ios:name";
        }
      }
    }
  }

  grouping config-interface-grouping {
    container interface {
      description
        "Configure Interfaces";
      list AppNav-Compress {
        description
          "Service-Context Virtual Interface Compress";
        key "name";
        leaf name {
          type uint16 {
            range "1..1000";
          }
        }
        uses interface-common-grouping;
      }
      list AppNav-UnCompress {
        description
          "Service-Context Virtual Interface UnCompress";
        key "name";
        leaf name {
          type uint16 {
            range "1..1000";
          }
        }
        uses interface-common-grouping;
      }
      list ATM {
        description
          "ATM interface";
        key "name";
        leaf name {
          type string;
        }
        uses interface-common-grouping;
      }
      container ATM-subinterface {
        list ATM {
          key "name";
          leaf name {
            type string;
          }
          leaf link-type {
            description
              "Link type for subinterface";
            type enumeration {
              enum "point-to-point";
              enum "multipoint";
            }
          }
          uses interface-common-grouping;
        }
      }
      list ATM-ACR {
        description
          "ATM-ACR interface";
        key "name";
        leaf name {
          type string {
            pattern "[0-9]";
          }
        }
      }
      container ATM-ACRsubinterface {
        list ATM-ACR {
          key "name";
          leaf name {
            type string {
              pattern "[0-9]\\.([0-9]/){3}[0-9]";
            }
          }
        }
      }
      list BDI {
        description
          "Bridge-Domain interface";
        key "name";
        leaf name {
          type string;
        }
        uses interface-common-grouping;
      }
      list CEM {
        description
          "Circuit Emulation interface";
        key "name";
        leaf name {
          type string {
            pattern "([0-9]/){2}[0-9]";
          }
        }
      }
      list CEM-ACR {
        description
          "Circuit Emulation interface";
        key "name";
        leaf name {
          type uint8 {
            range "0..255";
          }
        }
      }
      list Embedded-Service-Engine {
        description
          "cisco embedded service engine module";
        key "name";
        leaf name {
          type string;
        }
        uses interface-common-grouping;
      }
      list Ethernet {
        description
          "IEEE 802.3";
        key "name";
        leaf name {
          type string;
        }
        uses interface-common-grouping;
      }
      list FastEthernet {
        description
          "FastEthernet IEEE 802.3";
        key "name";
        leaf name {
          type string;
        }
        uses interface-common-grouping;
      }
      list ucse {
        description
          "Cisco ucse server";
        key "name";
        leaf name {
          type string;
        }
        uses interface-negotiation-grouping;
        uses interface-switchport-grouping;
        uses interface-common-grouping;
      }
      list Ethernet-Internal {
        description
          "Ethernet-Internal interface";
        key "name";
        leaf name {
          type string;
        }
        uses interface-negotiation-grouping;
        uses interface-switchport-grouping;
        uses interface-common-grouping;
      }
      list Service-Engine {
        description
          "Cisco service engine module";
        key "name";
        leaf name {
          type string;
        }
        uses interface-common-grouping;
      }
      list GigabitEthernet {
        description
          "GigabitEthernet IEEE 802.3z";
        key "name";
        leaf name {
          type string;
        }
        leaf media-type {
          description
            "Media type";
          type enumeration {
            enum "auto-select";
            enum "rj45";
            enum "sfp";
          }
        }
        leaf port-type {
          type enumeration {
            enum "nni";
          }
        }
        uses interface-common-grouping;
        uses interface-switchport-grouping;
      }
      list TwoGigabitEthernet {
        description
          "Two Gigabit Ethernet";
        key "name";
        leaf name {
          type string;
        }
        leaf media-type {
          description
            "Media type";
          type enumeration {
            enum "auto-select";
            enum "rj45";
            enum "sfp";
          }
        }
        leaf port-type {
          type enumeration {
            enum "nni";
          }
        }
        uses interface-common-grouping;
      }
      list FiveGigabitEthernet {
        description
          "Five Gigabit Ethernet";
        key "name";
        leaf name {
          type string;
        }
        leaf media-type {
          description
            "Media type";
          type enumeration {
            enum "auto-select";
            enum "rj45";
            enum "sfp";
          }
        }
        leaf port-type {
          type enumeration {
            enum "nni";
          }
        }
        uses interface-common-grouping;
      }
      list AppGigabitEthernet {
        description
          "App-hosting Gigabit Ethernet IEEE 802.3z";
        key "name";
        leaf name {
          type string;
        }
        leaf media-type {
          description
            "Media type";
          type enumeration {
            enum "auto-select";
            enum "rj45";
            enum "sfp";
          }
        }
        leaf port-type {
          type enumeration {
            enum "nni";
          }
        }
        uses interface-common-grouping;
        uses interface-switchport-grouping;
      }
      list TenGigabitEthernet {
        description
          "Ten Gigabit Ethernet";
        key "name";
        leaf name {
          type string;
        }
        leaf media-type {
          description
            "Media type";
          type enumeration {
            enum "auto-select";
            enum "rj45";
            enum "sfp";
          }
        }
        leaf port-type {
          type enumeration {
            enum "nni";
          }
        }
        uses interface-common-grouping;
      }
      list TwentyFiveGigabitEthernet {
        status obsolete;
        description
          "Twenty Five Gigabit Ethernet";
        key "name";
        leaf name {
          type string;
        }
        leaf media-type {
          description
            "Media type";
          type enumeration {
            enum "auto-select";
            enum "rj45";
            enum "sfp";
          }
        }
        leaf port-type {
          type enumeration {
            enum "nni";
          }
        }
        uses interface-common-grouping;
      }
      list TwentyFiveGigE {
        description
          "Twenty Five Gigabit Ethernet";
        key "name";
        leaf name {
          type string;
        }
        leaf media-type {
          description
            "Media type";
          type enumeration {
            enum "auto-select";
            enum "rj45";
            enum "sfp";
          }
        }
        leaf port-type {
          type enumeration {
            enum "nni";
          }
        }
        leaf fec {
          description
            "fec";
          type enumeration {
            enum "auto";
            enum "cl108";
            enum "cl74";
            enum "cl91";
            enum "off";
          }
        }
        uses interface-common-grouping;
      }
      list FortyGigabitEthernet {
        description
          "Forty Gigabit Ethernet";
        key "name";
        leaf name {
          type string;
        }
        leaf media-type {
          description
            "Media type";
          type enumeration {
            enum "auto-select";
            enum "rj45";
            enum "sfp";
          }
        }
        leaf port-type {
          type enumeration {
            enum "nni";
          }
        }
        uses interface-common-grouping;
      }
      list HundredGigE {
        description
          "Hundred Gigabit Ethernet";
        key "name";
        leaf name {
          type string;
        }
        leaf enable {
          description
            "To enable or disable HundredGig Traffic";
          type empty;
        }
        uses interface-common-grouping;
      }
      list Loopback {
        description
          "Loopback interface";
        key "name";
        leaf name {
          type uint32;
        }
        uses interface-common-grouping;
      }
      list LISP {
        description
          "Locator/ID Separation Protocol Virtual Interface";
        key "name";
        leaf name {
          type uint16 {
            range "0..65520";
          }
        }
        uses interface-common-grouping;
      }
      container LISP-subinterface {
        description
          "Locator/ID Separation Protocol Virtual Interface";
        list LISP {
          key "name";
          leaf name {
            type string {
              pattern "[0-9]*(. ?[1-9][0-9]*)*";
            }
          }
          uses interface-common-grouping;
        }
      }
      list nve {
        description
          "Network virtualization endpoint interface";
        key "name";
        leaf name {
          type uint16 {
            range "1..4096";
          }
        }
        container group-based {
          description
            "group based policy mode";
          leaf policy {
            type empty;
          }
        }
        container host-reachability {
          container protocol {
            leaf bgp {
              type empty;
            }
          }
        }
        container vxlan {
          container udp {
            leaf port {
              description
                "VxLAN dataplane UDP destination port for this NVE interface";
              type uint16 {
                range "1024..65535";
              }
            }
          }
        }
        container source-interface {
          description
            "Specify source interface for NVE";
          uses ios-ifc:interface-grouping;
        }
        container member-in-one-line {
          container member {
            list vni {
              description
                "Configure VNI information";
              key "vni-range";
              leaf vni-range {
                description
                  "VNI range or instance between 4096-16777215, example: 6010-6030 or 7115";
                type string;
              }
              leaf vrf {
                description
                  "Specify a particular VRF";
                must "/ios:native/ios:vrf/ios:definition[ios:name=current()] or /ios:native/ios:ip/ios:vrf[ios:name=current()]" {
                  error-message "VRF must be created 1st, deleted last";
                }
                type string;
              }
            }
          }
        }
        container member {
          list vni {
            description
              "Configure VNI information";
            key "vni-range";
            leaf vni-range {
              description
                "VNI range or instance between 4096-16777215, example: 6010-6030 or 7115";
              type string;
            }
            container default {
              uses nve-member-vni-no-grouping;
            }
            uses nve-member-vni-grouping;
            container no {
              uses nve-member-vni-no-grouping;
            }
          }
        }
        uses interface-common-grouping;
      }
      list overlay {
        description
          "Overlay interface";
        key "name";
        leaf name {
          type uint16 {
            range "0..512";
          }
        }
      }
      list Port-channel {
        description
          "Ethernet Channel of interfaces";
        key "name";
        leaf name {
          type uint32 {
            range "1..512";
          }
        }
        leaf pc-speed {
          description
            "Configure speed operation.";
          type enumeration {
            enum "10";
            enum "100";
            enum "1000";
            enum "nonegotiate";
            enum "auto";
          }
        }
        leaf load-balancing {
          description
            "Enable vlan or flow based load-balancing";
          type enumeration {
            enum "vlan";
            enum "flow";
          }
        }
        container punt-control {
          container enable {
            presence "true";
            leaf pps {
              type uint32 {
                range "1..1000000";
              }
            }
          }
        }
        container port-channel {
          description
            "Port Channel interface subcommands";
          leaf min-links {
            description
              "Minimum number of bundled ports needed to bring up      this port channel";
            type uint8 {
              range "2..8";
            }
          }
          leaf standalone-disable {
            description
              "Ports will go to suspended mode if peer does not respond. Use with [no] prefix for independent mode.";
            type empty;
          }
        }
        uses interface-common-grouping;
      }
      container Port-channel-subinterface {
        list Port-channel {
          key "name";
          leaf name {
            must "/ios:native/ios:interface/ios:Port-channel[ios:name=number(substring-before(current(), '.'))]" {
              error-message "To create a Port-channel subinterface, the Port-channel interface needs to be created 1st; vice versa for delete.";
            }
            type string;
          }
          uses interface-common-grouping;
        }
      }
      list pseudowire {
        description
          "Pseudowire Interface";
        key "name";
        leaf name {
          type uint32 {
            range "1..231072";
          }
        }
      }
      list SM {
        description
          "SM Interface";
        key "name";
        leaf name {
          type string {
            pattern "([0-9])+(/([0-9])+)?";
          }
        }
        uses interface-common-grouping;
      }
      list Cellular {
        description
          "Cellular Interface";
        key "name";
        leaf name {
          type string {
            pattern "([0-9])+(/([0-9])+)*";
          }
        }
        uses interface-common-grouping;
      }
      list Dialer {
        description
          "Dialer Interface";
        key "name";
        leaf name {
          type uint16 {
            range "0..255";
          }
        }
        uses interface-common-grouping;
      }
      list Vlan {
        description
          "Catalyst Vlans";
        key "name";
        leaf name {
          type uint16 {
            range "1..4094";
          }
        }
        uses interface-common-grouping;
      }
      list GMPLS {
        description
          "MPLS interface";
        key "name";
        leaf name {
          type uint16 {
            range "0..1000";
          }
        }
        uses interface-common-grouping;
      }
      list Group-Async {
        description
          "Async Group interface";
        key "name";
        leaf name {
          type uint16 {
            range "0..64";
          }
        }
        leaf physical-layer {
          description
            "Configure sync or async physical layer on serial interface";
          type enumeration {
            enum "async";
            enum "sync";
          }
        }
        uses interface-common-grouping;
      }
      list Multilink {
        description
          "Multilink-group interface";
        key "name";
        leaf name {
          type uint32 {
            range "1..2147483647";
          }
        }
        uses interface-common-grouping;
      }
      list Serial {
        description
          "Serial interface";
        key "name";
        leaf name {
          type string;
        }
        leaf down-when-looped {
          type empty;
        }
        uses interface-common-grouping;
      }
      list Async {
        description
          "Async interface";
        key "name";
        leaf name {
          type string;
        }
        uses interface-common-grouping;
      }
      list Tunnel {
        description
          "Tunnel interface";
        key "name";
        leaf name {
          type uint32;
        }
        uses interface-common-grouping;
        container qos {
          description
            "Quality of Service related commands";
          leaf pre-classify {
            description
              "Enable QOS classification before packets are tunnel encapsulated";
            type empty;
          }
        }
      }
      list Virtual-Template {
        description
          "Virtual Template interface";
        key "name";
        leaf name {
          type uint16 {
            range "1..4095";
          }
        }
        leaf type {
          description
            "type of the virtual-template";
          type enumeration {
            enum "ethernet";
            enum "serial";
            enum "tunnel";
            enum "vpn";
          }
        }
        uses interface-common-grouping;
      }
      list Virtual-PPP {
        description
          "Virtual PPP interface";
        key "name";
        leaf name {
          type uint32 {
            range "1..2147483647";
          }
        }
        uses interface-common-grouping;
      }
      list VirtualPortGroup {
        description
          "Virtual Port Group";
        key "name";
        leaf name {
          type uint16 {
            range "0..31";
          }
        }
        uses interface-common-grouping;
      }
      list vasileft {
        description
          "vasileft";
        key "name";
        leaf name {
          type uint16 {
            range "1..2000";
          }
        }
        uses interface-common-grouping;
      }
      list vasiright {
        description
          "vasiright";
        key "name";
        leaf name {
          type uint16 {
            range "1..2000";
          }
        }
        uses interface-common-grouping;
      }
      list Vif {
        description
          "PGM Multicast Host interface";
        key "name";
        leaf name {
          type uint32 {
            range "1..2147483647";
          }
        }
        uses interface-common-grouping;
      }
      list Wlan-GigabitEthernet {
        description
          "WLAN GigabitEthernet";
        key "name";
        leaf name {
          type string;
        }
        uses interface-switchport-grouping;
        uses interface-common-grouping;
      }
      list BD-VIF {
        description
          "Bridge-Domain Virtual IP interface";
        key "name";
        leaf name {
          type string;
        }
        uses interface-common-grouping;
      }
    }
  }
}
